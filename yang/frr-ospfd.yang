module frr-ospfd {
  yang-version 1.1;
  namespace "http://frrouting.org/yang/ospfd";
  prefix frr-ospfd;

  import ietf-inet-types {
    prefix inet;
  }
  import ietf-routing-types {
    prefix rt-types;
  }
  import ietf-yang-types {
    prefix yang;
  }
  import frr-vrf {
    prefix frr-vrf;
  }
  import frr-routing {
    prefix frr-rt;
  }
  import frr-interface {
    prefix frr-interface;
  }
  import frr-route-map {
    prefix frr-route-map;
  }
  import frr-route-types {
    prefix frr-route-types;
  }

  organization
    "FRRouting";
  contact
    "FRR Users List: <mailto:frog@lists.frrouting.org>
     FRR Development List: <mailto:dev@lists.frrouting.org>";
  description
    "This module defines a model for managing FRR OSPFd information.
     This YANG module augments the basic routing with additional
     OSPF information";

  revision 2022-07-29 {
    description
      "Shifted the model to better reflect ietf-ospf, added support for
       OSPF's operational state, and added parameters for unrepresented
       FRR clicmds";
    reference
      "draft-ietf-ospf-yang-29: YANG Data Model for OSPF Protocol.";
  }
  revision 2020-07-21 {
    description
      "Initial revision.";
  }

  identity ospf {
    base frr-rt:routing-protocol;
    description
      "'OSPF' routing ospf-protocol.";
  }

  identity area-type {
    description
      "Base identity for OSPF area type.";
  }

  identity normal-area {
    base area-type;
    description
      "OSPF normal area.";
  }

  identity stub-nssa-area {
    base area-type;
    description
      "OSPF stub or NSSA area.";
  }

  identity stub-area {
    base stub-nssa-area;
    description
      "OSPF stub area.";
  }

  identity nssa-area {
    base stub-nssa-area;
    description
      "OSPF Not-So-Stubby Area (NSSA).";
    reference
      "RFC 3101: The OSPF Not-So-Stubby Area
       (NSSA) Option";
  }

  identity ospf-lsa-type {
    description
      "Base identity for OSPFv2 and OSPFv3
       Link State Advertisement (LSA) types";
  }

  identity ospfv2-lsa-type {
    base ospf-lsa-type;
    description
      "OSPFv2 LSA types";
  }

  identity ospfv2-router-lsa {
    base ospfv2-lsa-type;
    description
      "OSPFv2 Router LSA - Type 1";
  }

  identity ospfv2-network-lsa {
    base ospfv2-lsa-type;
    description
      "OSPFv2 Network LSA - Type 2";
  }

  identity ospfv2-summary-lsa-type {
    base ospfv2-lsa-type;
    description
      "OSPFv2 Summary LSA types";
  }

  identity ospfv3-network-summary-lsa {
    base ospfv2-summary-lsa-type;
    description
      "OSPFv2 Network Summary LSA - Type 3";
  }

  identity ospfv2-asbr-summary-lsa {
    base ospfv2-summary-lsa-type;
    description
      "OSPFv2 AS Boundary Router (ASBR) Summary LSA - Type 4";
  }

  identity ospfv2-external-lsa-type {
    base ospfv2-lsa-type;
    description
      "OSPFv2 External LSA types";
  }

  identity ospfv2-as-external-lsa {
    base ospfv2-external-lsa-type;
    description
      "OSPFv2 AS External LSA - Type 5";
  }

  identity ospfv2-nssa-lsa {
    base ospfv2-external-lsa-type;
    description
      "OSPFv2 Not-So-Stubby-Area (NSSA) LSA - Type 7";
  }

  identity ospfv2-opaque-lsa-type {
    base ospfv2-lsa-type;
    description
      "OSPFv2 Opaque LSA types";
  }

  identity ospfv2-link-scope-opaque-lsa {
    base ospfv2-opaque-lsa-type;
    description
      "OSPFv2 Link-Scoped Opaque LSA - Type 9";
  }

  identity ospfv2-area-scope-opaque-lsa {
    base ospfv2-opaque-lsa-type;
    description
      "OSPFv2 Area-Scoped Opaque LSA - Type 10";
  }

  identity ospfv2-as-scope-opaque-lsa {
    base ospfv2-opaque-lsa-type;
    description
      "OSPFv2 AS-Scoped Opaque LSA - Type 11";
  }

  identity ospfv2-unknown-lsa-type {
    base ospfv2-lsa-type;
    description
      "OSPFv2 Unknown LSA type";
  }

  identity ospfv2-lsa-option {
    description
      "Base identity for OSPFv2 LSA option flags.";
  }

  identity mt-bit {
    base ospfv2-lsa-option;
    description
      "MT bit, When set, the router supports multi-topology as
       in RFC 4915.";
  }

  identity v2-dc-bit {
    base ospfv2-lsa-option;
    description
      "DC bit, When set, the router supports demand circuits.";
  }

  identity v2-p-bit {
    base ospfv2-lsa-option;
    description
      "P bit, wnly used in type-7 LSA. When set, an NSSA
       border router should translate the type-7 LSA
       to a type-5 LSA.";
  }

  identity mc-flag {
    base ospfv2-lsa-option;
    description
      "MC Bit, when set, the router supports MOSPF.";
  }

  identity v2-e-flag {
    base ospfv2-lsa-option;
    description
      "E Bit, this bit describes the way AS-external LSAs
       are flooded.";
  }

  identity o-bit {
    base ospfv2-lsa-option;
    description
      "O bit, when set, the router is opaque-capable as in
       RFC 5250.";
  }

  identity v2-dn-bit {
    base ospfv2-lsa-option;
    description
      "DN bit, when a type 3, 5 or 7 LSA is sent from a PE
       to a CE, the DN bit must be set. See RFC 4576.";
  }

  identity ospfv3-lsa-option {
    description
      "Base identity for OSPF LSA options flags.";
  }

  identity af-bit {
    base ospfv3-lsa-option;
    description
      "AF bit, when set, the router supports OSPFv3 Address
       Families as in RFC 5838.";
  }

  identity dc-bit {
    base ospfv3-lsa-option;
    description
      "DC bit, when set, the router supports demand circuits.";
  }

  identity r-bit {
    base ospfv3-lsa-option;
    description
      "R bit, when set, the originator is an active router.";
  }

  identity n-bit {
    base ospfv3-lsa-option;
    description
      "N bit, when set, the router is attached to an NSSA";
  }

  identity e-bit {
    base ospfv3-lsa-option;
    description
      "E bit, this bit describes the way AS-external LSAs
       are flooded";
  }

  identity v6-bit {
    base ospfv3-lsa-option;
    description
      "V6 bit, if clear, the router/link should be excluded
       from IPv6 routing calculation";
  }

  identity ospfv3-lsa-type {
    base ospf-lsa-type;
    description
      "OSPFv3 LSA types.";
  }

  identity ospfv3-router-lsa {
    base ospfv3-lsa-type;
    description
      "OSPFv3 Router LSA - Type 0x2001";
  }

  identity ospfv3-network-lsa {
    base ospfv3-lsa-type;
    description
      "OSPFv3 Network LSA - Type 0x2002";
  }

  identity ospfv3-summary-lsa-type {
    base ospfv3-lsa-type;
    description
      "OSPFv3 Summary LSA types";
  }

  identity ospfv3-inter-area-prefix-lsa {
    base ospfv3-summary-lsa-type;
    description
      "OSPFv3 Inter-area Prefix LSA - Type 0x2003";
  }

  identity ospfv3-inter-area-router-lsa {
    base ospfv3-summary-lsa-type;
    description
      "OSPFv3 Inter-area Router LSA - Type 0x2004";
  }

  identity ospfv3-external-lsa-type {
    base ospfv3-lsa-type;
    description
      "OSPFv3 External LSA types";
  }

  identity ospfv3-as-external-lsa {
    base ospfv3-external-lsa-type;
    description
      "OSPFv3 AS-External LSA - Type 0x4005";
  }

  identity ospfv3-nssa-lsa {
    base ospfv3-external-lsa-type;
    description
      "OSPFc3 Not-So-Stubby-Area (NSSA) LSA - Type 0x2007";
  }

  identity ospfv3-link-lsa {
    base ospfv3-lsa-type;
    description
      "OSPFv3 Link LSA - Type 0x0008";
  }

  identity ospfv3-intra-area-prefix-lsa {
    base ospfv3-lsa-type;
    description
      "OSPFv3 Intra-area Prefix LSA - Type 0x2009";
  }

  identity ospfv3-router-information-lsa {
    base ospfv3-lsa-type;
    description
      "OSPFv3 Router Information LSA - Types 0x800C,
       0xA00C, and 0xC00C";
  }

  identity ospfv3-unknown-lsa-type {
    base ospfv3-lsa-type;
    description
      "OSPFv3 Unknown LSA type";
  }

  identity ospfv3-prefix-option {
    description
      "Base identity for OSPFv3 Prefix Options.";
  }

  identity nu-bit {
    base ospfv3-prefix-option;
    description
      "NU Bit, when set, the prefix should be excluded
       from IPv6 unicast calculations.";
  }

  identity la-bit {
    base ospfv3-prefix-option;
    description
      "LA bit, when set, the prefix is actually an IPv6
       interface address of the Advertising Router.";
  }

  identity p-bit {
    base ospfv3-prefix-option;
    description
      "P bit, when set, the NSSA area prefix should be
       translated to an AS External LSA and advertised
       by the translating NSSA Border Router.";
  }

  identity dn-bit {
    base ospfv3-prefix-option;
    description
      "DN bit, when set, the inter-area-prefix LSA or
       AS-external LSA prefix has been advertised as an
       L3VPN prefix.";
  }

  identity ospfv2-extended-prefix-flag {
    description
      "Base identity for extended prefix TLV flag.";
  }

  identity a-flag {
    base ospfv2-extended-prefix-flag;
    description
      "Attach flag, when set it indicates that the prefix
       corresponds and a route what is directly connected to
       the advertising router..";
  }

  identity node-flag {
    base ospfv2-extended-prefix-flag;
    description
      "Node flag, when set, it indicates that the prefix is
       used to represent the advertising node, e.g., a loopback
       address.";
  }

  identity lsa-log-reason {
    description
      "Base identity for an LSA log reason.";
  }

  identity lsa-refresh {
    base lsa-log-reason;
    description
      "Identity used when the LSA is logged
       as a result of receiving a refresh LSA.";
  }

  identity lsa-content-change {
    base lsa-log-reason;
    description
      "Identity used when the LSA is logged
       as a result of a change in the content
       of the LSA.";
  }

  identity lsa-purge {
    base lsa-log-reason;
    description
      "Identity used when the LSA is logged
       as a result of being purged.";
  }

  identity informational-capability {
    description
      "Base identity for router informational capabilities.";
  }

  identity graceful-restart {
    base informational-capability;
    description
      "When set, the router is capable of restarting
       gracefully.";
    reference
      "RFC 3623: Graceful OSPF Restart
       RFC 5187: OSPFv3 Graceful Restart";
  }

  identity graceful-restart-helper {
    base informational-capability;
    description
      "When set, the router is capable of acting as
       a graceful restart helper.";
    reference
      "RFC 3623: Graceful OSPF Restart
       RFC 5187: OSPFv3 Graceful Restart";
  }

  identity stub-router {
    base informational-capability;
    description
      "When set, the router is capable of acting as
       an OSPF Stub Router.";
    reference
      "RFC 6987: OSPF Stub Router Advertisement";
  }

  identity traffic-engineering {
    base informational-capability;
    description
      "When set, the router is capable of OSPF traffic
       engineering.";
    reference
      "RFC 3630: Traffic Engineering (TE) Extensions
       to OSPF Version 2
       RFC 5329: Traffic Engineering (TE) Extensions
       to OSPF Version 3";
  }

  identity p2p-over-lan {
    base informational-capability;
    description
      "When set, the router is capable of OSPF Point-to-Point
       over LAN.";
    reference
      "RFC 5309: Point-to-Point Operation over LAN
       in Link State Routing Protocols";
  }

  identity experimental-te {
    base informational-capability;
    description
      "When set, the router is capable of OSPF experimental
       traffic engineering.";
    reference
      "RFC 4973: OSPF-xTE OSPF Experimental Traffic
       Engineering";
  }

  identity router-lsa-bit {
    description
      "Base identity for Router-LSA bits.";
  }

  identity vlink-end-bit {
    base router-lsa-bit;
    description
      "V bit, when set, the router is an endpoint of one or
       more virtual links.";
  }

  identity asbr-bit {
    base router-lsa-bit;
    description
      "E bit, when set, the router is an AS Boundary
       Router (ASBR).";
  }

  identity abr-bit {
    base router-lsa-bit;
    description
      "B bit, when set, the router is an Area Border
       Router (ABR).";
  }

  identity nssa-bit {
    base router-lsa-bit;
    description
      "Nt bit, when set, the router is an NSSA border router
       that is unconditionally translating NSSA LSAs into
       AS-external LSAs.";
  }

  identity shortcut-bit {
    base router-lsa-bit;
    /* XXX Unknown bit letter */
    description
      "? bit, when set, the router is shortcut-ABR enabled.";
  }

  identity extended-prefix-range-bit {
    description
      "Base identity for extended prefix range TLV bits.";
  }

  identity extended-prefix-range-ia-bit {
    base extended-prefix-range-bit;
    description
      "Inter-Area flag. If set, advertisement is of inter-area type.";
  }

  identity prefix-sid-bit {
    description
      "Base identity for prefix sid sub-tlv bits.";
  }

  identity prefix-np-bit {
    base prefix-sid-bit;
    description
      "No-PHP flag.";
  }

  identity prefix-m-bit {
    base prefix-sid-bit;
    description
      "Mapping server flag.";
  }

  identity prefix-e-bit {
    base prefix-sid-bit;
    description
      "Explicit-NULL flag.";
  }

  identity prefix-v-bit {
    base prefix-sid-bit;
    description
      "Value/Index flag.";
  }

  identity prefix-l-bit {
    base prefix-sid-bit;
    description
      "Local flag.";
  }

  identity adj-sid-bit {
    description
      "Base identity for adj sid sub-tlv bits.";
  }

  identity adj-b-bit {
    base adj-sid-bit;
    description
      "Backup flag.";
  }

  identity adj-vi-bit {
    base adj-sid-bit;
    description
      "Value/Index flag.";
  }

  identity adj-lo-bit {
    base adj-sid-bit;
    description
      "Local/Global flag.";
  }

  identity adj-g-bit {
    base adj-sid-bit;
    description
      "Group flag.";
  }

  identity adj-p-bit {
    base adj-sid-bit;
    description
      "Persistent flag.";
  }

  /* Policy types to be removed later, once policy Yang finalized */

  typedef plist-ref {
    type string;
  }

  typedef access-list-ref {
    type string;
  }

  typedef ospf-area-id {
    type union {
      type inet:ipv4-address;
      type uint32;
    }
    description
      "OSPF Area ID.";
  }

  typedef ospf-link-metric {
    type uint16 {
      range "0 .. 65535";
    }
    description
      "OSPF Link Metric - 16-bit unsigned integer.";
  }

  typedef auth-type {
    type enumeration {
      enum "null" {
        value 0;
        description
          "Use null authentication.";
      }
      enum "simple" {
        value 1;
        description
          "Use simple authentication.";
      }
      enum "cryptographic" {
        value 2;
        description
          "Use message-digest authentication.";
      }
    }
    description
      "Authentication type.";
  }

  /*
   * RPC data types
   */

  typedef neighbor-ref {
    type leafref {
      path "/frr-interface:lib/frr-interface:interface/frr-ospfd:ospf/"
        + "frr-ospfd:state/frr-ospfd:neighbors/frr-ospfd:neighbor/"
        + "frr-ospfd:neighbor-router-id";
      require-instance false;
    }
    description
      "Reference to a neighbor.";
  }

  typedef ospf-instance-ref {
    type leafref {
      path "/frr-rt:routing/frr-rt:control-plane-protocols"
         + "/frr-rt:control-plane-protocol/frr-rt:name";
    }
    description
      "Reference to an OSPF instance ID.";
  }

  /*
   * ----------------------------------------------
   * Link State Database (LSD) Types and Identities
   * ----------------------------------------------
   */

  typedef if-state {
    type enumeration {
      enum "down" {
        value 1;
        description
          "Interface down state.";
      }
      enum "loopback" {
        value 2;
        description
          "Interface loopback state.";
      }
      enum "waiting" {
        value 3;
        description
          "Interface waiting state.";
      }
      enum "point-to-point" {
        value 4;
        description
          "Interface point-to-point state.";
      }
      enum "dr" {
        value 5;
        description
          "Interface Designated Router (DR) state.";
      }
      enum "bdr" {
        value 6;
        description
          "Interface Backup Designated Router (BDR) state.";
      }
      enum "dr-other" {
        value 7;
        description
          "Interface Other Designated Router state.";
      }
    }
    description
      "OSPF interface state type.";
  }

  typedef nbr-state {
    type enumeration {
      enum "down" {
        value 1;
        description
          "Neighbor down state.";
      }
      enum "attempt" {
        value 2;
        description
          "Neighbor attempt state.";
      }
      enum "init" {
        value 3;
        description
          "Neighbor init state.";
      }
      enum "2-way" {
        value 4;
        description
          "Neighbor 2-Way state.";
      }
      enum "exstart" {
        value 5;
        description
          "Neighbor exchange start state.";
      }
      enum "exchange" {
        value 6;
        description
          "Neighbor exchange state.";
      }
      enum "loading" {
        value 7;
        description
          "Neighbor loading state.";
      }
      enum "full" {
        value 8;
        description
          "Neighbor full state.";
      }
    }
    description
      "OSPF neighbor state type.";
  }

  typedef gr-restart-reason {
    /* frr specific model */
    type enumeration {
      enum "unknown-restart" {
        value 0;
        description
          "Uknown restart.";
      }
      enum "sw-restart" {
        value 1;
        description
          "Software restart.";
      }
      enum "sw-upgrade" {
        value 2;
        description
          "Software reload/upgrade.";
      }
      enum "switch-redundant-card" {
        value 3;
        description
          "Switch to redundant control processor.";
      }
      enum "invalid-reason-code" {
        value 4;
        description
          "Invalid restart.";
      }
    }
  }

  typedef gr-exit-reason {
    /* frr specific model */
    type enumeration {
      enum "exit-none" {
        value 0;
        description
          "No exit reason.";
      }
      enum "inprogress" {
        value 1;
        description
          "Graceful restart in progress.";
      }
      enum "topo-chg" {
        value 2;
        description
          "Topology has changed.";
      }
      enum "grace-timeout" {
        value 3;
        description
          "Grace period expired.";
      }
      enum "completed" {
        value 4;
        description
          "Graceful restart completed.";
      }
    }
  }

  typedef gr-reject-reason {
    /* frr specific model */
    type enumeration {
      enum "rejected-none" {
        value 0;
        description
          "No reject reason.";
      }
      enum "support-disabled" {
        value 1;
        description
          "Graceful restart is not supported.";
      }
      enum "not-a-valid-neighbour" {
        value 2;
        description
          "Not a valud neighbour.";
      }
      enum "planned-only-restart" {
        value 3;
        description
          "Can only support planned graceful restarts";
      }
      enum "topo-change-rtxmt-list" {
        value 4;
        description
          "Topology change in retransmit list";
      }
      enum "lsa-age-more" {
        value 5;
        description
          "Link state advertisments are older than grace period";
      }
      enum "restarting" {
        value 6;
        description
          "Currently restarting";
      }
    }
  }

  typedef opaque-id {
    type uint32 {
      range "0 .. 16777215";
    }
    description
      "Opaque ID - 24-bit unsigned integer.";
  }

  typedef fletcher-checksum16-type {
    type string {
      pattern "(0x)?[0-9a-fA-F]{4}";
    }
    description
      "Fletcher 16-bit checksum in hex-string format 0xXXXX.";
    reference
      "RFC 905: ISO Transport Protocol specification
       ISO DP 8073";
  }

  typedef router-link-type {
    type enumeration {
      enum "point-to-point-link" {
        value 1;
        description
          "Point-to-Point link to Router";
      }
      enum "transit-network-link" {
        value 2;
        description
          "Link to transit network identified by
           Designated-Router (DR)";
      }
      enum "stub-network-link" {
        value 3;
        description
          "Link to stub network identified by subnet";
      }
      enum "virtual-link" {
        value 4;
        description
          "Virtual link across transit area";
      }
    }
    description
      "OSPF Router Link Type.";
  }

  typedef ospf-metric {
    type uint32 {
      range "0 .. 16777215";
    }
    description
      "OSPF Metric - 24-bit unsigned integer.";
  }

  typedef pce-domain-type {
    type enumeration {
      enum "ospf-area-id" {
        value 1;
        description
          "Indicates that the visible domain type is an OSPF Area.";
      }
      enum "as-number" {
        value 2;
        description
          "Indicates that the visible domain type is an AS";
      }
    }
  }

  typedef route-type {
    type enumeration {
      enum "min" {
        value 0;
        description
          "OSPF min path.";
      }
      enum "intra-area" {
        value 1;
        description
          "OSPF intra-area route.";
      }
      enum "inter-area" {
        value 2;
        description
          "OSPF inter-area route.";
      }
      enum "external-1" {
        value 3;
        description
          "OSPF type 1 external route.";
      }
      enum "external-2" {
        value 4;
        description
          "OSPF type 2 external route.";
      }
      enum "max" {
        value 5;
        description
          "OSPF mac path.";
      }
      /*
      enum "nssa-1" {
        description "OSPF type 1 NSSA route.";
      }
      enum "nssa-2" {
        description "OSPF type 2 NSSA route.";
      }
      */
    }
    description
      "OSPF path/route type.";
  }

  typedef destination-type {
    type enumeration {
      enum "router" {
        value 1;
        description
          "Destination is a router.";
      }
      enum "network" {
        value 2;
        description
          "Destination is a network.";
      }
      enum "discard" {
        value 3;
        description
          "Destination is to be discarded.";
      }
    }
    description
      "The destination type of a route.";
  }

  typedef area-type {
    type enumeration {
      enum "default" {
        value 0;
        description
          "Default area type.";
      }
      enum "stub" {
        value 1;
        description
          "Stub area type.";
      }
      enum "nssa" {
        value 2;
        description
          "Not so stubby area type.";
      }
      enum "max" {
        value 3;
        description
          "Max area type.";
      }
    }
    description
      "The type of an area.";
  }

  typedef pce-capabilities {
    type bits {
      bit gmpls-link {
        position 0;
        description
          "Means that can compute paths with GMPLS link constraints.";
      }
      bit bidirectional {
        position 1;
        description
          "Means that can compute bidirectional paths.";
      }
      bit diverse-path {
        position 2;
        description
          "Means that can compute diverse paths.";
      }
      bit load-balance {
        position 3;
        description
          "Means that can compute load-balanced paths.";
      }
      bit synchronized {
        position 4;
        description
          "Means that can compute synchronized paths.";
      }
      bit objectives {
        position 5;
        description
          "Means that can support multiple objective functons.";
      }
      bit additive {
        position 6;
        description
          "Means that can support additive path constraints.";
      }
      bit prioritization {
        position 7;
        description
          "Means that can support requests for prioritization.";
      }
      bit multiple-req {
        position 8;
        description
          "Means that can support multiple requests per message.";
      }
    }
    description
      "PCE capabilities";
  }

  /*
   * -------------------------------------------
   * Link State Database (LSD) Operational State
   * -------------------------------------------
   */

  grouping tlv {
    description
      "Type-Length-Value (TLV)";
    leaf type {
      type uint16;
      description
        "TLV type.";
    }
    leaf length {
      type uint16;
      description
        "TLV length (octets).";
    }
    leaf value {
      type yang:hex-string;
      description
        "TLV value.";
    }
  }

  grouping unknown-tlvs {
    description
      "Unknown TLVs grouping - Used for unknown TLVs or
       unknown sub-TLVs.";
    container unknown-tlvs {
      description
        "All unknown TLVs.";
      list unknown-tlv {
        description
          "Unknown TLV.";
        uses tlv;
      }
    }
  }

  grouping extended-tlvs {
    /* frr specific model */
    description
      "subTLVs implemented in frr beyond the default types 1-9";
    container local-and-remote-te-router-id {
      description
        "Type 10 subTLVs. Local/Remote router Identifiers. If specified,
         ignore link-id subTLVs and use instead.";
      leaf local-router-id {
        type rt-types:router-id;
        description
          "Local TE Router ID.";
      }
      leaf remote-router-id {
        type rt-types:router-id;
        description
          "Remote TR Router ID.";
      }
    }
    container link-local-remote-id {
      description
        "Type subTLV 11. Link Local/Remote Identifiers";
      leaf link-local-id {
        type uint32;
      }
      leaf link-remote-id {
        type uint32;
      }
    }
    leaf remote-as-number {
      type uint32;
      description
        "Type 21 subTLVs. Specifies the AS number of a neighboring AS";
    }
    leaf ipv4-remote-asbr-id {
      type inet:ipv4-address;
      description
        "Type 22 subTLVs. Specifies the ASBR Ip address of the previously
         specified AS";
    }
    leaf unidirectional-link-delay {
      type uint32 {
        range "0..16777215";
      }
      units "microseconds";
      description
        "Type 27 subTLVs. Delay in Microseconds.";
    }
    container min-max-unidirectional-link-delay {
      description
        "Type 28 subTLVs.";
      leaf min-delay {
        type uint32 {
          range "0..16777215";
        }
        units "microseconds";
        description
          "Minimum delay in Microseconds";
      }
      leaf max-delay {
        type uint32 {
          range "0..16777215";
        }
        units "microseconds";
        description
          "Maximum delay in Microseconds.";
      }
    }
    leaf unidirectional-delay-variation {
      type uint32 {
        range "0..16777215";
      }
      units "microseconds";
      description
        "Type 29 subTLVs. Link delay variation in Microseconds.";
    }
    leaf unidirectional-link-loss {
      type uint32 {
        range "0..16777214";
      }
      description
        "Type 20 subTLVs. Percentage loss of link packets on a link. Basic unit
         is 0.000003%, leading to a maximum 50.331642%.";
    }
    leaf unidirectional-residual-bandwidth {
      type rt-types:bandwidth-ieee-float32;
      units "Bytes/Sec";
      description
        "Type 31 subTLVs. Residual unidirectional bandwidth in IEEE floating
         point format.";
    }
    leaf unidirectional-available-bandwidth {
      type rt-types:bandwidth-ieee-float32;
      units "Bytes/Sec";
      description
        "Type 32 subTLVs. Available unidirectional bandwidth in IEEE floating
         point format.";
    }
    leaf unidirectional-utilized-bandwidth {
      type rt-types:bandwidth-ieee-float32;
      units "Bytes/Sec";
      description
        "Type 33 subTLVs. Utilized unidirectional bandwidth in IEEE floating
         point format.";
    }
  }

  grouping pce-bitfield {
    leaf scope-flags {
      type bits {
        bit L {
          position 0;
          description
            "PCE intra-area path computation bit.";
        }
        bit R {
          position 1;
          description
            "PCE inter-area TE LSP computation bit.";
        }
        bit Rd {
          position 2;
          description
            "Default PCE inter-area TE LSP computation bit.";
        }
        bit S {
          position 3;
          description
            "PCE inter-as TE LSP computation bit.";
        }
        bit Sd {
          position 4;
          description
            "Default PCE inter-as TE LSP computation bit.";
        }
        bit Y {
          position 5;
          description
            "PCE inter-layer TE LSP computation bit.";
        }
      }
      description
        "PCE path scope flags bitfield";
    }
    leaf pref-l {
      type uint8 {
        range "0..7";
      }
      description
        "PCE's preference for intra-area TE LSP computation.";
    }
    leaf pref-r {
      type uint8 {
        range "0..7";
      }
      description
        "PCE's preference for inter-area TE LSP computation.";
    }
    leaf pref-s {
      type uint8 {
        range "0..7";
      }
      description
        "PCE's preference for inter-AS TE LSP computation.";
    }
    leaf pref-y {
      type uint8 {
        range "0..7";
      }
      description
        "PCE's preference for inter-layer TE LSP computation.";
    }
  }

  grouping pced-tlv {
    /* frr specific model */
    description
      "PCE Discovery TLV.";
    leaf pce-address {
      type inet:ipv4-address;
      description
        "Type 1 subTLV. Ip address to reach the PCE.";
    }
    container path-scope {
      description
        "Type 2 subTLV. PCE path computation scope.";
      uses pce-bitfield;
    }
    container domain {
      description
        "Type 3 subTLV. PCE domain type and ID.";
      leaf type {
        type pce-domain-type;
      }
      leaf id {
        type uint32;
        description
          "PCE domain ID.";
      }
    }
    container neighbors {
      description
        "Type 4 subTLV. List of Neighbor's PCE domain types and IDs.";
      list neighbor {
        leaf type {
          type pce-domain-type;
        }
        leaf id {
          type uint32;
          description
            "PCE domain ID. Either an Area ID or As depending on domain-type";
        }
      }
    }
    leaf capabilities {
      type pce-capabilities;
      description
        "Type 5 subTLV. Indicates a list of PCE capability flags.";
    }
  }

  grouping node-tag-tlv {
    description
      "OSPF Node Admin Tag TLV grouping.";
    list node-tag {
      description
        "List of tags.";
      leaf tag {
        type uint32;
        description
          "Node admin tag value.";
      }
    }
  }

  grouping router-capabilities-tlv {
    description
      "OSPF Router Capabilities TLV grouping.";
    reference
      "RFC 7770: OSPF Router Capabilities";
    container router-informational-capabilities {
      description
        "OSPF Router Informational Flag Definitions.";
      leaf-list informational-capabilities {
        type identityref {
          base informational-capability;
        }
        description
          "Informational capability list. This list will
           contains the identities for the informational
           capabilities supported by router.";
      }
    }
    /*
    list informational-capabilities-flags {
      leaf informational-flag {
        type uint32;
        description
          "Individual informational capability flag.";
      }
      description
        "List of informational capability flags. This will
         return all the 32-bit informational flags irrespective
         of whether or not they are known to the device.";
    }
    list functional-capabilities {
      leaf functional-flag {
        type uint32;
        description
          "Individual functional capability flag.";
      }
      description
        "List of functional capability flags. This will
         return all the 32-bit functional flags irrespective
         of whether or not they are known to the device.";
    }
    */
  }

  grouping grace-lsa-opaque {
    /* frr specific model */
    /* XXX This TLV should have link-local scope only */
    container grace-lsa-opaque {
      description
        "OSPFv2 Graceful Restart opaque LSA.";
      reference
        "RFC 3623: Graceful OSPF Restart Appendex-A";
      container grace-period-tlv {
        description
          "Type 1 tlv.";
        leaf grace-period {
          type uint32;
          units "seconds";
          mandatory true;
          description
            "The number of seconds that a neighbor should be advertised as
             fully adjacent despite the state of database synchronization.";
        }
      }
      container restart-reason-tlv {
        description
          "Type 2 tlv.";
        leaf restart-reason {
          type gr-restart-reason;
          mandatory true;
          description
            "The graceful restart reason.";
        }
      }
      container if-address-tlv {
        description
          "Type 3 tlv.";
        leaf if-address {
          type inet:ipv4-address;
          /* XXX Set up condition for mandatory true? */
          description
            "IP address of subnet associated with grace-LSA. Required on all
             but point-to-point segments.";
        }
      }
    }
  }

  grouping sid-sub-tlv {
    description
      "SID/Label sub-TLV grouping.";
    container sid-sub-tlv {
      description
        "Used to advertise the SID/Label associated with a
         prefix or adjacency.";
      leaf sid {
        type uint32;
        description
          "Segment Identifier (SID) - A 20 bit label or
           32 bit SID.";
      }
    }
  }

  grouping sr-algorithm-tlv {
    description
      "SR algorithm TLV grouping.";
    reference
      "draft-ietf-ospf-sr-yang-18: YANG Data Model for OSPF Segment Routing";
    container sr-algorithm-tlv {
      description
        "All SR algorithm (type 8) TLVs.";
      leaf-list sr-algorithm {
        type uint8;
        description
          "The Segment Routing (SR) algorithms that the router is
           currently using";
      }
    }
  }

  grouping sid-range-tlvs {
    description
      "SID Range TLV grouping.";
    reference
      "draft-ietf-ospf-sr-yang-18: YANG Data Model for OSPF Segment Routing";
    container sid-range-tlvs {
      description
        "List of SID range (type 9) TLVs. Also known as SRGB TLV";
      list sid-range-tlv {
        description
          "SID range TLV.";
        leaf range-size {
          type uint32 {
            range "0..16777215";
          }
          description
            "The SID range.";
        }
        uses sid-sub-tlv;
      }
    }
  }

  grouping local-block-tlvs {
    description
      "The SR local block TLV contains the range of labels reserved for local
       SIDs.";
    reference
      "draft-ietf-ospf-sr-yang-18: YANG Data Model for OSPF Segment Routing";
    container local-block-tlvs {
      description
        "List of SRLB (type 14) TLVs.";
      list local-block-tlv {
        description
          "SRLB TLV.";
        leaf range-size {
          type uint32 {
            range "0..16777215";
          }
          description
            "The SID range.";
        }
        uses sid-sub-tlv;
      }
    }
  }

  grouping node-msd-tlv {
    /* frr specific model */
    description
      "The Node/MSD TLV";
    reference
      "RFC 8476: Signaling Maximum SID Depth (MSD) Using OSPF";
    container node-msd-tlvs {
      description
        "List of pairs of MDS (type 12) TLVs.";
      list node-msd-tlv {
        description
          "MSD TLV.";
        leaf type {
          type uint8;
          description
            "IGP MSD Type.";
          /* Will always be 1 in frr */
        }
        leaf value {
          type uint8;
          description
            "Link MSD of router.";
        }
      }
    }
  }

  grouping extended-prefix-range-tlvs {
    description
      "Extended prefix range (type 2) TLV grouping.";
    reference
      "draft-ietf-ospf-sr-yang-18: YANG Data Model for OSPF Segment Routing";
    container extended-prefix-range-tlvs {
      description
        "The list of range of prefixes.";
      list extended-prefix-range-tlv {
        description
          "The range of prefixes.";
        leaf prefix-length {
          type uint8;
          description
            "Length of prefix in bits.";
        }
        leaf af {
          type uint8;
          description
            "Address family for the prefix.";
        }
        leaf range-size {
          type uint16;
          description
            "The number of prefixes covered by the
             advertisement.";
        }
        container extended-prefix-range-flags {
          description
            "Extended Prefix Range TLV flags.";
          leaf-list bits {
            type identityref {
              base extended-prefix-range-bit;
            }
            description
              "Extended prefix range TLV flags list.";
          }
        }
        leaf prefix {
          type inet:ipv4-prefix;
          description
            "Address prefix.";
        }
        // uses prefix-sid-sub-tlvs;
        uses unknown-tlvs;
      }
    }
  }

  grouping prefix-sid-sub-tlvs {
    description
      "Prefix Segment ID (SID, type 2) sub-TLVs.";
    reference
      "draft-ietf-ospf-sr-yang-18: YANG Data Model for OSPF Segment Routing";
    container prefix-sid-sub-tlvs {
      description
        "Prefix SID sub-TLV.";
      list prefix-sid-sub-tlv {
        description
          "Prefix SID sub-TLV.";
        container prefix-sid-flags {
          description
            "Segment Identifier (SID) Flags.";
          leaf-list bits {
            type identityref {
              base prefix-sid-bit;
            }
            description
              "Prefix SID Sub-TLV flag bits list.";
          }
        }
        leaf mt-id {
          type uint8;
          description
            "Multi-topology ID.";
        }
        leaf algorithm {
          type uint8;
          description
            "The algorithm associated with the prefix-SID.";
        }
        leaf sid {
          type uint32;
          description
            "An index, label or value.";
        }
      }
    }
  }

  grouping adj-sid-sub-tlvs {
    description
      "(Lan) Adjacency SID subTLVs'.";
    reference
      "draft-ietf-ospf-sr-yang-18: YANG Data Model for OSPF Segment Routing";
    container adj-sid-sub-tlvs {
      description
        "Adjacency SID (type 2) optional sub-TLVs.";
      list adj-sid-sub-tlv {
        description
          "List of Adjacency SID sub-TLVs.";
        container adj-sid-flags {
          description
            "Adj-sid sub-tlv flags.";
          leaf-list bits {
            type identityref {
              base adj-sid-bit;
            }
            description
              "Adj sid sub-tlv flags list.";
          }
        }
        leaf mt-id {
          type uint8;
          description
            "Multi-topology ID.";
        }
        leaf weight {
          type uint8;
          description
            "Weight used for load-balancing.";
        }
        leaf sid {
          type uint32;
          description
            "Segment Identifier (SID) index/label/value.";
        }
      }
    }
    container lan-adj-sid-sub-tlvs {
      description
        "LAN Adjacency SID (type 3) optional sub-TLVs.";
      list lan-adj-sid-sub-tlv {
        description
          "List of LAN adjacency SID sub-TLVs.";
        container lan-adj-sid-flags {
          description
            "LAN adj-sid sub-tlv flags.";
          leaf-list bits {
            type identityref {
              base adj-sid-bit;
            }
            description
              "LAN adj sid sub-tlv flags list.";
          }
        }
        leaf mt-id {
          type uint8;
          description
            "Multi-topology ID.";
        }
        leaf weight {
          type uint8;
          description
            "Weight used for load-balancing.";
        }
        leaf neighbor-router-id {
          type rt-types:router-id;
          description
            "Neighbor router ID.";
        }
        leaf sid {
          type uint32;
          description
            "Segment Identifier (SID) index/label/value.";
        }
      }
    }
  }

  grouping dynamic-hostname-tlv {
    description
      "Dynamic Hostname TLV";
    reference
      "RFC 5642: Dynamic Hostnames for OSPF";
    leaf hostname {
      type string {
        length "1..255";
      }
      description
        "Dynamic Hostname";
    }
  }

  grouping sbfd-discriminator-tlv {
    description
      "Seamless BFD Discriminator TLV";
    reference
      "RFC 7884: S-BFD Discriminators in OSPF";
    list sbfd-discriminators {
      description
        "List of S-BFD Discriminators";
      leaf sbfd-discriminator {
        type uint32;
        description
          "Individual S-BFD Discriminator.";
      }
    }
  }

  grouping maximum-sid-depth-tlv {
    description
      "Maximum SID Depth (MSD) TLV";
    reference
      "RFC 8476: Signaling Maximum Segment Depth (MSD)
       using OSPF";
    list msd-type {
      description
        "List of Maximum Segment Depth (MSD) tuples";
      leaf msd-type {
        type uint8;
        description
          "Maximum Segment Depth (MSD) type";
      }
      leaf msd-value {
        type uint8;
        description
          "Maximum Segment Depth (MSD) value for the type";
      }
    }
  }

  grouping ospf-router-lsa-bits {
    description
      "Router LSA Bits - Currently common for OSPFv2 and
       OSPFv3 but it may diverge with future augmentations.";
    container router-bits {
      description
        "Router LSA Bits.";
      leaf-list rtr-lsa-bits {
        type identityref {
          base router-lsa-bit;
        }
        description
          "Router LSA bits list. This list will contain
           identities for the bits which are set in the
           Router-LSA bits.";
      }
    }
  }

  grouping ospfv2-router-link {
    description
      "OSPFv2 router link.";
    leaf link-id {
      type inet:ipv4-address;
      description
        "Router-LSA Link ID";
    }
    leaf link-data {
      /*
      XXX uint32 from OSPFv3 not supported

      type union {
        type inet:ipv4-address;
        type uint32;
      }
      */
      type inet:ipv4-address;
      description
        "Router-LSA Link data.";
    }
    leaf type {
      type router-link-type;
      description
        "Router-LSA Link type.";
    }
  }

  grouping ospfv2-lsa-body {
    description
      "OSPFv2 LSA body.";
    container router {
      when "derived-from-or-self(../../header/type, 'ospfv2-router-lsa')" {
        description
          "Only applies to Router-LSAs.";
      }
      description
        "Router LSA.";
      uses ospf-router-lsa-bits;
      leaf num-of-links {
        type uint16;
        description
          "Number of links in Router LSA.";
      }
      container links {
        description
          "All router Links.";
        list link {
          description
            "Router LSA link.";
          uses ospfv2-router-link;
          container topologies {
            description
              "All topologies for the link.";
            list topology {
              description
                "Topology specific information.";
              leaf mt-id {
                type uint8;
                description
                  "The MT-ID for the topology enabled on
                   the link.";
              }
              leaf metric {
                type ospf-link-metric;
                description
                  "Metric for the topology.";
              }
            }
          }
        }
      }
    }
    container network {
      when "derived-from-or-self(../../header/type, 'ospfv2-network-lsa')" {
        description
          "Only applies to Network LSAs.";
      }
      description
        "Network LSA.";
      leaf network-mask {
        type yang:dotted-quad;
        description
          "The IP address mask for the network.";
      }
      container attached-routers {
        description
          "All attached routers.";
        leaf-list attached-router {
          type inet:ipv4-address;
          description
            "List of the routers attached to the network.";
        }
      }
    }
    container summary {
      when "derived-from(../../header/type, 'ospfv2-summary-lsa-type')" {
        description
          "Only applies to Summary LSAs.";
      }
      description
        "Summary LSA.";
      leaf network-mask {
        type inet:ipv4-address;
        description
          "The IP address mask for the network";
      }
      container topologies {
        description
          "All topologies for the summary LSA.";
        list topology {
          description
            "Topology specific information.";
          leaf mt-id {
            type uint8;
            description
              "The MT-ID for the topology enabled for
               the summary.";
          }
          leaf metric {
            type ospf-metric;
            description
              "Metric for the topology.";
          }
        }
      }
    }
    container external {
      when "derived-from(../../header/type, 'ospfv2-external-lsa-type')" {
        description
          "Only applies to AS-external LSAs and NSSA LSAs.";
      }
      description
        "External LSA.";
      leaf network-mask {
        type inet:ipv4-address;
        description
          "The IP address mask for the network";
      }
      container topologies {
        description
          "All topologies for the external.";
        list topology {
          description
            "Topology specific information.";
          leaf mt-id {
            type uint8;
            description
              "The MT-ID for the topology enabled for the
               external or NSSA prefix.";
          }
          leaf flags {
            type bits {
              bit E {
                description
                  "When set, the metric specified is a Type 2
                   external metric.";
              }
            }
            description
              "Flags.";
          }
          leaf metric {
            type ospf-metric;
            description
              "Metric for the topology.";
          }
          leaf forwarding-address {
            type inet:ipv4-address;
            description
              "Forwarding address.";
          }
          leaf external-route-tag {
            type uint32;
            description
              "Route tag for the topology.";
          }
        }
      }
    }
    container opaque {
      when "derived-from(../../header/type, 'ospfv2-opaque-lsa-type')" {
        description
          "Only applies to Opaque LSAs.";
      }
      description
        "Opaque LSA.";
      container ri-opaque {
        description
          "OSPF Router Information (RI) opaque LSA.";
        reference
          "RFC 7770: OSPF Router Capabilities";
        container router-capabilities-tlv {
          description
            "Informational and functional router capabilities";
          uses router-capabilities-tlv;
        }
        /*
        container node-tag-tlvs {
          description
            "All node tag TLVs.";
          list node-tag-tlv {
            description
              "Node tag TLV.";
            uses node-tag-tlv;
          }
        }
        container dynamic-hostname-tlv {
          description "OSPF Dynamic Hostname";
          uses dynamic-hostname-tlv;
        }
        container sbfd-discriminator-tlv {
          description "OSPF S-BFD Discriminators";
          uses sbfd-discriminator-tlv;
        }
        container maximum-sid-depth-tlv {
          description "OSPF Maximum SID Depth (MSD) values";
          uses maximum-sid-depth-tlv;
        }
        */
        container pced-tlv {
          description
            "The PCE discovery tlv.";
          uses pced-tlv;
        }
        uses sr-algorithm-tlv;
        uses sid-range-tlvs;
        uses local-block-tlvs;
        uses node-msd-tlv;
        uses unknown-tlvs;
      }
      container te-opaque {
        description
          "OSPFv2 Traffic Engineering (TE) opaque LSA.";
        reference
          "RFC 3630: Traffic Engineering (TE)
           Extensions to OSPFv2";
        container router-address-tlv {
          description
            "Router address TLV.";
          leaf router-address {
            type inet:ipv4-address;
            description
              "Router address.";
          }
        }
        container link-tlv {
          description
            "Describes a single link, and it is constructed
             of a set of Sub-TLVs.";
          leaf link-type {
            type router-link-type;
            mandatory true;
            description
              "Link type.";
          }
          leaf link-id {
            type inet:ipv4-address;
            mandatory true;
            description
              "Link ID.";
          }
          container local-if-ipv4-addrs {
            description
              "All local interface IPv4 addresses.";
            leaf-list local-if-ipv4-addr {
              type inet:ipv4-address;
              description
                "List of local interface IPv4 addresses.";
            }
          }
          container remote-if-ipv4-addrs {
            description
              "All remote interface IPv4 addresses.";
            leaf-list remote-if-ipv4-addr {
              type inet:ipv4-address;
              description
                "List of remote interface IPv4 addresses.";
            }
          }
          leaf te-metric {
            type uint32;
            description
              "TE metric.";
          }
          leaf max-bandwidth {
            type rt-types:bandwidth-ieee-float32;
            units "Bytes/Sec";
            description
              "Maximum bandwidth.";
          }
          leaf max-reservable-bandwidth {
            type rt-types:bandwidth-ieee-float32;
            units "Bytes/Sec";
            description
              "Maximum reservable bandwidth.";
          }
          container unreserved-bandwidths {
            description
              "All unreserved bandwidths.";
            list unreserved-bandwidth {
              description
                "List of unreserved bandwidths for different
                 priorities.";
              leaf priority {
                type uint8 {
                  range "0 .. 7";
                }
                description
                  "Priority from 0 to 7.";
              }
              leaf unreserved-bandwidth {
                type rt-types:bandwidth-ieee-float32;
                units "Bytes/Sec";
                description
                  "Unreserved bandwidth.";
              }
            }
          }
          leaf admin-group {
            type uint32;
            description
              "Administrative group/Resource Class/Color.";
          }
          uses extended-tlvs;
          uses unknown-tlvs;
        }
      }
      uses grace-lsa-opaque;
      container extended-prefix-opaque {
        description
          "All extended prefix TLVs in the LSA.";
        list extended-prefix-tlv {
          description
            "Extended prefix TLV.";
          leaf route-type {
            type enumeration {
              enum "unspecified" {
                value 0;
                description
                  "Unspecified.";
              }
              enum "intra-area" {
                value 1;
                description
                  "OSPF intra-area route.";
              }
              enum "inter-area" {
                value 3;
                description
                  "OSPF inter-area route.";
              }
              enum "external" {
                value 5;
                description
                  "OSPF External route.";
              }
              enum "nssa" {
                value 7;
                description
                  "OSPF NSSA external route.";
              }
            }
            description
              "Route type.";
          }
          container flags {
            description
              "Prefix Flags.";
            leaf-list extended-prefix-flags {
              type identityref {
                base ospfv2-extended-prefix-flag;
              }
              description
                "Extended prefix TLV flags list. This list will
                 contain identities for the prefix flags that
                 are set in the extended prefix flags.";
            }
          }
          leaf prefix {
            type inet:ipv4-prefix;
            description
              "Address prefix.";
          }
          uses prefix-sid-sub-tlvs;
          uses unknown-tlvs;
        }
        uses extended-prefix-range-tlvs;
      }
      container extended-link-opaque {
        description
          "All extended link TLVs in the LSA.";
        container extended-link-tlv {
          description
            "Extended link TLV.";
          uses ospfv2-router-link;
          container maximum-sid-depth-tlv {
            description
              "OSPF Maximum SID Depth (MSD) values";
            uses maximum-sid-depth-tlv;
          }
          uses adj-sid-sub-tlvs;
          leaf remote-if-address {
            /* frr specific model */
            type inet:ipv4-address;
            description
              "Type 32768 subTLV for experimental Cisco use. Remote interface
               Address";
          }
          uses unknown-tlvs;
        }
      }
    }
  }

  grouping ospfv3-lsa-options {
    description
      "OSPFv3 LSA options";
    container lsa-options {
      description
        "OSPFv3 LSA options.";
      leaf-list lsa-options {
        type identityref {
          base ospfv3-lsa-option;
        }
        description
          "OSPFv3 LSA Option flags list. This list will contain
           the identities for the OSPFv3 LSA options that are
           set for the LSA.";
      }
    }
  }

  grouping ospfv3-lsa-prefix {
    description
      "OSPFv3 LSA prefix.";
    leaf prefix {
      type inet:ipv4-prefix;
      description
        "LSA Prefix.";
    }
    container prefix-options {
      description
        "Prefix options.";
      leaf-list prefix-options {
        type identityref {
          base ospfv3-prefix-option;
        }
        description
          "OSPFv3 prefix option flag list. This list will
           contain the identities for the OSPFv3 options
           that are set for the OSPFv3 prefix.";
      }
    }
  }

  grouping ospfv3-lsa-external {
    description
      "AS-External and NSSA LSA.";
    leaf metric {
      type ospf-metric;
      description
        "Metric";
    }
    leaf flags {
      type bits {
        bit E {
          description
            "When set, the metric specified is a Type 2
             external metric.";
        }
        bit F {
          description
            "When set, a Forwarding Address is included
             in the LSA.";
        }
        bit T {
          description
            "When set, an External Route Tag is included
             in the LSA.";
        }
      }
      description
        "Flags.";
    }
    leaf referenced-ls-type {
      type identityref {
        base ospfv3-lsa-type;
      }
      description
        "Referenced Link State type.";
    }
    leaf unknown-referenced-ls-type {
      type uint16;
      description
        "Value for an unknown Referenced Link State type.";
    }
    uses ospfv3-lsa-prefix;
    leaf forwarding-address {
      type inet:ipv6-address;
      description
        "Forwarding address.";
    }
    leaf external-route-tag {
      type uint32;
      description
        "Route tag.";
    }
    leaf referenced-link-state-id {
      type uint32;
      description
        "Referenced Link State ID.";
    }
  }

  grouping ospfv3-lsa-body {
    description
      "OSPFv3 LSA body.";
    container router {
      when "derived-from-or-self(../../header/type, 'ospfv3-router-lsa')" {
        description
          "Only applies to Router LSAs.";
      }
      description
        "Router LSA.";
      uses ospf-router-lsa-bits;
      uses ospfv3-lsa-options;
      container links {
        description
          "All router link.";
        list link {
          description
            "Router LSA link.";
          leaf interface-id {
            type uint32;
            description
              "Interface ID for link.";
          }
          leaf neighbor-interface-id {
            type uint32;
            description
              "Neighbor's Interface ID for link.";
          }
          leaf neighbor-router-id {
            type rt-types:router-id;
            description
              "Neighbor's Router ID for link.";
          }
          leaf type {
            type router-link-type;
            description
              "Link type: 1 - Point-to-Point Link
                          2 - Transit Network Link
                          3 - Stub Network Link
                          4 - Virtual Link";
          }
          leaf metric {
            type ospf-link-metric;
            description
              "Link Metric.";
          }
        }
      }
    }
    container network {
      when "derived-from-or-self(../../header/type, 'ospfv3-network-lsa')" {
        description
          "Only applies to Network LSAs.";
      }
      description
        "Network LSA.";
      uses ospfv3-lsa-options;
      container attached-routers {
        description
          "All attached routers.";
        leaf-list attached-router {
          type rt-types:router-id;
          description
            "List of the routers attached to the network.";
        }
      }
    }
    container inter-area-prefix {
      when "derived-from-or-self(../../header/type, 'ospfv3-inter-area-prefix-lsa')" {
        description
          "Only applies to Inter-Area-Prefix LSAs.";
      }
      description
        "Prefix LSA.";
      leaf metric {
        type ospf-metric;
        description
          "Inter-Area Prefix Metric";
      }
      uses ospfv3-lsa-prefix;
    }
    container inter-area-router {
      when "derived-from-or-self(../../header/type, 'ospfv3-inter-area-router-lsa')" {
        description
          "Only applies to Inter-Area-Router LSAs.";
      }
      description
        "Inter-Area-Router LSA.";
      uses ospfv3-lsa-options;
      leaf metric {
        type ospf-metric;
        description
          "AS Boundary Router (ASBR) Metric.";
      }
      leaf destination-router-id {
        type rt-types:router-id;
        description
          "The Router ID of the ASBR described by the LSA.";
      }
    }
    container as-external {
      when "derived-from-or-self(../../header/type, 'ospfv3-as-external-lsa')" {
        description
          "Only applies to AS-external LSAs.";
      }
      description
        "AS-External LSA.";
      uses ospfv3-lsa-external;
    }
    container nssa {
      when "derived-from-or-self(../../header/type, 'ospfv3-nssa-lsa')" {
        description
          "Only applies to NSSA LSAs.";
      }
      description
        "NSSA LSA.";
      uses ospfv3-lsa-external;
    }
    container link {
      when "derived-from-or-self(../../header/type, 'ospfv3-link-lsa')" {
        description
          "Only applies to Link LSAs.";
      }
      description
        "Link LSA.";
      leaf rtr-priority {
        type uint8;
        description
          "Router priority for DR election. A router with a
           higher priority will be preferred in the election
           and a value of 0 indicates the router is not
           eligible to become Designated Router or Backup
           Designated Router (BDR).";
      }
      uses ospfv3-lsa-options;
      leaf link-local-interface-address {
        type inet:ipv6-address;
        description
          "The originating router's link-local
           interface address for the link.";
      }
      leaf num-of-prefixes {
        type uint32;
        description
          "Number of prefixes.";
      }
      container prefixes {
        description
          "All prefixes for the link.";
        list prefix {
          description
            "List of prefixes associated with the link.";
          uses ospfv3-lsa-prefix;
        }
      }
    }
    container intra-area-prefix {
      when "derived-from-or-self(../../header/type, 'ospfv3-intra-area-prefix-lsa')" {
        description
          "Only applies to Intra-Area-Prefix LSAs.";
      }
      description
        "Intra-Area-Prefix LSA.";
      leaf referenced-ls-type {
        type identityref {
          base ospfv3-lsa-type;
        }
        description
          "Referenced Link State type.";
      }
      leaf unknown-referenced-ls-type {
        type uint16;
        description
          "Value for an unknown Referenced Link State type.";
      }
      leaf referenced-link-state-id {
        type uint32;
        description
          "Referenced Link State ID.";
      }
      leaf referenced-adv-router {
        type rt-types:router-id;
        description
          "Referenced Advertising Router.";
      }
      leaf num-of-prefixes {
        type uint16;
        description
          "Number of prefixes.";
      }
      container prefixes {
        description
          "All prefixes in this LSA.";
        list prefix {
          description
            "List of prefixes in this LSA.";
          uses ospfv3-lsa-prefix;
          leaf metric {
            type ospf-metric;
            description
              "Prefix Metric.";
          }
        }
      }
    }
    container router-information {
      when "derived-from-or-self(../../header/type, 'ospfv3-router-information-lsa')" {
        description
          "Only applies to Router Information LSAs (RFC 7770).";
      }
      description
        "Router Information LSA.";
      reference
        "RFC 7770: Extensions for Advertising Router
         Capabilities";
      container router-capabilities-tlv {
        description
          "Informational and functional router capabilities";
        uses router-capabilities-tlv;
      }
      container node-tag-tlvs {
        description
          "All node tag tlvs.";
        list node-tag-tlv {
          description
            "Node tag tlv.";
          uses node-tag-tlv;
        }
      }
      container dynamic-hostname-tlv {
        description
          "OSPF Dynamic Hostname";
        uses dynamic-hostname-tlv;
      }
      container sbfd-discriminator-tlv {
        description
          "OSPF S-BFD Discriminators";
        uses sbfd-discriminator-tlv;
      }
    }
  }

  grouping lsa-header {
    description
      "Common LSA for OSPFv2 and OSPFv3";
    leaf age {
      type uint16;
      mandatory true;
      description
        "LSA age.";
    }
    leaf type {
      type identityref {
        base ospf-lsa-type;
      }
      mandatory true;
      description
        "LSA type";
    }
    leaf adv-router {
      type rt-types:router-id;
      mandatory true;
      description
        "LSA advertising router.";
    }
    leaf seq-num {
      type uint32;
      mandatory true;
      description
        "LSA sequence number.";
    }
    leaf checksum {
      type fletcher-checksum16-type;
      mandatory true;
      description
        "LSA checksum.";
    }
    leaf length {
      type uint16;
      mandatory true;
      description
        "LSA length including the header.";
    }
  }

  grouping ospfv2-lsa {
    description
      "OSPFv2 LSA - LSAs are uniquely identified by
       the <LSA Type, Link-State ID, Advertising Router>
       tuple with the sequence number differentiating
       LSA instances.";
    container header {
      must "(derived-from(type, "
         + "'ospfv2-opaque-lsa-type') and "
         + "opaque-id and opaque-type) or "
         + "(not(derived-from(type, "
         + "'ospfv2-opaque-lsa-type')) "
         + "and not(opaque-id) and not(opaque-type))" {
        description
          "Opaque type and ID only apply to Opaque LSAs.";
      }
      description
        "Decoded OSPFv2 LSA header data.";
      container lsa-options {
        description
          "LSA options.";
        leaf-list lsa-option {
          type identityref {
            base ospfv2-lsa-option;
          }
          description
            "LSA option flags list. This list will contain
             the identities for the identities for the OSPFv2
             LSA options that are set.";
        }
      }
      leaf lsa-id {
        type yang:dotted-quad;
        mandatory true;
        description
          "Link-State ID.";
      }
      leaf opaque-type {
        type uint8;
        description
          "Opaque type.";
      }
      leaf opaque-id {
        type opaque-id;
        description
          "Opaque ID.";
      }
      uses lsa-header;
    }
    container body {
      description
        "Decoded OSPFv2 LSA body data.";
      uses ospfv2-lsa-body;
    }
  }

  grouping ospfv3-lsa {
    description
      "Decoded OSPFv3 LSA.";
    container header {
      description
        "Decoded OSPFv3 LSA header data.";
      leaf lsa-id {
        type uint32;
        mandatory true;
        description
          "OSPFv3 LSA ID.";
      }
      uses lsa-header;
    }
    container body {
      description
        "Decoded OSPF LSA body data.";
      uses ospfv3-lsa-body;
    }
  }

  grouping lsa-common {
    description
      "Common fields for OSPF LSA representation.";
    leaf decode-completed {
      type boolean;
      description
        "The OSPF LSA body was successfully decoded other than
         unknown TLVs. Unknown LSAs types and OSPFv2 unknown
         opaque LSA types are not decoded. Additionally,
         malformed LSAs are generally not accepted and will
         not be in the Link State Database.";
    }
    leaf raw-data {
      type yang:hex-string;
      description
        "The complete LSA in network byte
         order hexadecimal as received or originated.";
    }
  }

  grouping lsa-key {
    description
      "OSPF LSA key - the database key for each LSA of a given
       type in the Link State DataBase (LSDB).";
    leaf lsa-id {
      /*
      XXX uint32 is included for OSPFv3, which is not supported under ospfd

      type union {
        type yang:dotted-quad;
        type uint32;
      }
      */
      type yang:dotted-quad;
      description
        "Link-State ID.";
    }
    leaf adv-router {
      type rt-types:router-id;
      description
        "Advertising router.";
    }
  }

  grouping lsa {
    description
      "OSPF LSA.";
    uses lsa-common;
    choice version {
      description
        "OSPFv2 or OSPFv3 LSA body.";
      container ospfv2 {
        description
          "OSPFv2 LSA";
        uses ospfv2-lsa;
      }
      /*
       * ospfv3 version unsupported by ospfd (needs ospf6d)

      container ospfv3 {
        description "OSPFv3 LSA";
        uses ospfv3-lsa;
      }
      */
    }
  }

  grouping lsa-database {
    uses lsa-key;
    uses lsa {
      /*
      refine "version/ospfv2/ospfv2" {
        must "derived-from-or-self( "
           + "/frr-rt:routing/frr-rt:control-plane-protocols/"
           + "frr-rt:control-plane-protocol/frr-rt:type, 'ospf')" {
          description
            "OSPFv2 LSA. (ospfd)";
        }
      }
      */
      /* 
      refine "version/ospfv3/ospfv3" {
        must "derived-from-or-self( "
           + "/frr-rt:routing/frr-rt:control-plane-protocols/"
           + "frr-rt:control-plane-protocol/frr-rt:type, 'ospf6')" {
          description "OSPFv3 LSA. (ospf6d)";
        }
      }
      */
    }
  }

  /*
   * ----------------------------
   * End of LSD Operational State
   * ----------------------------
   */

  grouping range-grouping {
    container ranges {
      list range {
        key "prefix";
        description
          "A list of range objects";
        leaf prefix {
          type inet:ipv4-prefix;
          description
            "Area range prefix";
        }
        leaf advertise {
          type boolean;
          default "true";
          description
            "Advertise this range";
        }
        leaf cost {
          type ospf-metric;
          description
            "Metric for this range";
        }
        leaf substitute {
          type inet:ipv4-prefix;
          description
            "Network prefix to be announced instead of range";
        }
      }
    }
  }

  grouping shortcut-grouping {
    container shortcut {
      description
        "Shortcut configuration.";
      leaf configuration {
        type enumeration {
          enum "default" {
            value 0;
            description
              "Default shortcutting behavior";
          }
          enum "enable" {
            value 1;
            description
              "Enable shortcutting through the area";
          }
          enum "disable" {
            value 2;
            description
              "Disable shortcutting through the area";
          }
        }
        default "default";
      }
    }
  }

  grouping authentication-group {
    container authentication {
      description
        "Enable authentication on this link.";
      leaf type {
        type auth-type;
      }
      leaf simple-key {
        when "enum-value(../type) = 1" {
          description
            "A simple key consists of only a simple password.";
        }
        type string;
        description
          "The OSPF password.";
      }
      container mds-keys {
        when "enum-value(../type) = 2" {
          description
            "A message digest key set consists of an id and password.";
        }
        list mds-key {
          key "id key";
          leaf id {
            type uint8;
            description
              "Key id";
          }
          leaf key {
            type string;
            description
              "The OSPF password.";
          }
        }
      }
    }
  }

  grouping interface-common-attributes {
    description
      "Common configuration for all types of interfaces,
       including virtual links.";
    leaf hello-interval {
      type uint16 {
        range "1..65535";
      }
      units "seconds";
      description
        "Interval between hello packets (seconds). It must
         be the same for all routers on the same network.
         Different networks, implementations, and deployments
         will use different hello-intervals. A sample value
         for a LAN network would be 10 seconds.";
      reference
        "RFC 2328: OSPF Version 2, Appendix C.3";
    }
    leaf retransmit-interval {
      type uint16 {
        range "1..65535";
        /* IETF max was 3000 */
      }
      units "seconds";
      description
        "Interval between retransmitting unacknowledged Link
         State Advertisements (LSAs) (seconds). This should
         be well over the round-trip transmit delay for
         any two routers on the network. A sample value
         would be 5 seconds.";
      reference
        "RFC 2328: OSPF Version 2, Appendix C.3";
    }
    leaf transmit-delay {
      type uint16 {
        range "1..65535";
      }
      units "seconds";
      description
        "Estimated time needed to transmit Link State Update
         (LSU) packets on the interface (seconds). LSAs have
         their age incremented by this amount when advertised
         on the interface. A sample value would be 1 second.";
      reference
        "RFC 2328: OSPF Version 2, Appendix C.3";
    }
    uses authentication-group;
  }

  grouping virtual-link-group {
    container virtual-links {
      when "derived-from-or-self(../area-type, 'normal-area') and ../area-id = '0.0.0.0'" {
        description
          "Virtual links must be in backbone area.";
      }
      list virtual-link {
        key "transit-area-id router-id";
        description
          "Virtual link parameters.";
        leaf transit-area-id {
          type leafref {
            path "../../../../area/area-id";
          }
          must "derived-from-or-self("
            + "../../../../area[area-id=current()]/area-type, 'normal-area')"
            + " and "
            + "../../../../area[area-id=current()]/area-id != '0.0.0.0'" {
            error-message "Virtual link transit area must be non-zero";
            description
              "Virtual-link transit area must be non-zero area.";
          }
        }
        leaf router-id {
          type rt-types:router-id;
          description
            "Router ID of the remote ABR.";
        }
        leaf dead-interval {
          type uint16;
          units "seconds";
          must "../dead-interval > ../hello-interval" {
            error-message
              "The dead interval must be larger than the hello interval";
            description
              "The value must be greater than the 'hello-interval'.";
          }
          default "40";
          description
            "Interval after which a neighbor is declared down (seconds) if
             hello packets are not received. It is typically 3 or 4 times the
             hello-interval. A typical value for LAN networks is 40 seconds.";
          reference
            "RFC 2328: OSPF Version 2, Appendix C.3";
        }
        uses interface-common-attributes {
          refine "hello-interval" {
            default "10";
          }
          refine "retransmit-interval" {
            default "5";
          }
          refine "transmit-delay" {
            default "1";
          }
          refine "authentication/type" {
            default "null";
          }
        }
        container state {
          config false;
          description
            "Operational state of all a virtual link.";
          uses interface-common-state;
        }
      }
    }
  }

  grouping area-groupings {
    container areas {
      list area {
        key "area-id";
        description
          "A list of area objects";
        leaf area-id {
          type ospf-area-id;
        }
        leaf area-type {
          type identityref {
            base area-type;
          }
          default "normal-area";
          description
            "Area type.";
        }
        container authentication {
          presence "Enable authentication.";
          description
            "Enable authentication in this area.";
          leaf type {
            type auth-type;
            default "null";
          }
        }
        leaf summary {
          when "derived-from(../area-type,'stub-nssa-area')" {
            description
              "Summary advertisement into the stub/NSSA area.";
          }
          type boolean;
          description
            "Enable/Disable summary advertisement into the stub or NSSA area.";
        }
        leaf default-cost {
          when "derived-from(../area-type,'stub-nssa-area')" {
            description
              "Cost for LSA default route advertised into the
               stub or NSSA area.";
          }
          type ospf-metric;
          default "1";
          description
            "Set the summary default route cost for a stub or NSSA area.";
        }
        container nssa {
          when "derived-from-or-self(../area-type,'nssa-area')" {
            description
              "NSSA only config parameters.";
          }
          leaf translate {
            type enumeration {
              enum "never" {
                description
                  "NSSA-ABR to never translate.";
              }
              enum "candidate" {
                description
                  "NSSA-ABR for translate election.";
              }
              enum "always" {
                description
                  "NSSA-ABR to always translate.";
              }
            }
            default "candidate";
            description
              "NSSA translator role.";
          }
          leaf suppress-fa {
            type boolean;
            default "false";
            description
              "Suppress forwarding address.";
          }
        }
        leaf export-list {
          type access-list-ref;
          description
            "Filter for networks announced to other areas.";
        }
        leaf import-list {
          type access-list-ref;
          description
            "Filter for networks from other areas announced to the specified
             one.";
        }
        container filter-list {
          container in {
            leaf prefix {
              type plist-ref;
              description
                "Filter networks being advertised by other OSPF areas.";
            }
          }
          container out {
            leaf prefix {
              type plist-ref;
              description
                "Filter networks being advertised by this OSPF area.";
            }
          }
        }
        uses range-grouping;
        uses shortcut-grouping;
        container state {
          config false;
          description
            "Area-scope operational state container.";
          uses area-state;
        }
        uses virtual-link-group;
      }
    }
  }

  /* router ospf attributes */

  grouping route-ospf-attributes {
    leaf use-arp {
      type boolean;
      default "true";
      description
        "ARP for neighbor table entry.";
    }
    leaf explicit-router-id {
      type rt-types:router-id;
      /* Not mandatory, since the router-id can be configured automatically */
      description
        "Router-id for the OSPF process.";
    }
    leaf capability-opaque {
      type boolean;
      default "false";
      description
        "Opaque LSA.";
    }
    leaf compatible-rfc1583 {
      type boolean;
      default "false";
      description
        "Compatible with RFC 1583.";
    }
    container log-adjacency-changes {
      /* frr specific model */
      presence "Log adjacency changes.";
      leaf detail {
        type boolean;
        default "false";
        description
          "Log additional detail.";
      }
    }
    leaf send-extra-data-zebra {
      type boolean;
      default "false";
      description
        "Send extra data to the Zebra daemon.";
    }
    leaf default-metric {
      type uint32 {
        range "0..16777214";
      }
      description
        "Metric of redistributed routes.";
    }
    leaf write-multiplier {
      type uint8 {
        range "1..100";
      }
      default "20";
      description
        "Maximum number of interfaces serviced per write.";
    }
    leaf passive-interface-default {
      type boolean;
      default "false";
      description
        "Suppress routing updates on interfaces by default.";
    }
    leaf abr-type {
      type enumeration {
        enum "cisco" {
          value 1;
          description
            "Alternative ABR, Cisco implementation.";
        }
        enum "ibm" {
          value 2;
          description
            "Alternative ABR,  IBM implementation.";
        }
        enum "shortcut" {
          value 3;
          description
            "Shortcut ABR.";
        }
        enum "standard" {
          value 4;
          description
            "Standard behavior (RFC 2328).";
        }
      }
      default "cisco";
    }
    container router-info {
      /*
       * XXX In frr (ospfd.h), no router capabilities config information is
       * actually stored in the ospf data structure. 
       */
      presence "Router info is enabled on this router";
      choice type {
        case as {
          leaf as {
            type boolean;
            default true;
            description
              "Enable the Router Information functionality with AS flooding scope.";
          }
        }
        case area {
          leaf area {
            type boolean;
            description
              "Enable the Router Information functionality with Area flooding scope.";
          }
        }
      }
      container pce {
        /* frr specific model */
        description
          "Path Computational Element (PCE) RI information.";
        leaf address {
          type inet:ipv4-address;
          description
            "Stable ID address of the PCE.";
        }
        container scope {
          description
            "PCE scope bitfield.";
          uses pce-bitfield;
        }
        container as {
          leaf domain {
            type uint32 {
              range "0..65535";
            }
            description
              "AS number where the PCE AS visibility for path computation.";
          }
          leaf neighbor {
            type uint32 {
              range "0..65535";
            }
            description
              "AS number of PCE neighbors.";
          }
        }
        leaf capabilities {
          type pce-capabilities;
        }
      }
    }
  }

  /* OSPF Auto cost config attributes */

  grouping auto-cost-group {
    container auto-cost {
      /* auto-cost reference bandwidth is always enabled in FRR */
      /*
      leaf enable {
        type boolean;
        description
          "Enable/Disable interface auto-cost.";
      }
      */
      leaf reference-bandwidth {
        type uint32 {
          range "1..4294967";
        }
        /* IETF units were Mbps */
        units "Kbps";
        default "100000";
        description
          "The reference bandwidth in terms of Kilobits per second.";
      }
    }
  }

  /* OSPF Graceful restart config attributes */

  grouping graceful-restart-group {
    container graceful-restart {
      description
        "Graceful restart config state.";
      reference
        "RFC 3623: OSPF Graceful Restart
         RFC 5187: OSPFv3 Graceful Restart";
      leaf enable {
        type boolean;
        default "false";
        description
          "Enable/Disable graceful restart as defined in RFC 3623
           for OSPFv2 and RFC 5187 for OSPFv3.";
      }
      leaf helper-enable {
        type boolean;
        default "false";
        description
          "Enable graceful restart helper support for restarting
           routers (RFC 3623 Section 3).";
      }
      leaf restart-interval {
        type uint16 {
          range "1..1800";
        }
        units "seconds";
        default "120";
        description
          "Interval to attempt graceful restart prior
           to failing (RFC 3623 Section B.1) (seconds)";
      }
      leaf helper-strict-lsa-checking {
        type boolean;
        default "true";
        description
          "Terminate graceful restart when an LSA topology change
           is detected (RFC 3623 Section B.2).";
      }
      leaf helper-only-planned-restart {
        /* frr specific model */
        type boolean;
        default "false";
        description
          "Only support as Helper in the case of planned restarts";
      }
      leaf supported-grace-time {
        /* frr specific model */
        type uint16 {
          range "10..1800";
        }
        units "seconds";
        default "1800";
        description
          "Support as Helper for this configured grace period";
      }
    }
  }

  grouping metric-common-group {
    leaf metric {
      type ospf-metric;
      description
        "OSPF default metric.";
    }
    leaf metric-type {
      type enumeration {
        enum "type-1" {
          value 1;
        }
        enum "type-2" {
          value 2;
        }
      }
      description
        "Metric type (1/2).";
    }
    leaf route-map {
      type frr-route-map:route-map-ref;
      description
        "Route map reference.";
    }
  }

  grouping default-info-group {
    container default-information {
      leaf originate {
        type enumeration {
          enum "none" {
            value 0;
            description
              "Don't advertise default route.";
          }
          enum "zebra" {
            value 1;
            description
              "Always default route only to Zebra.";
          }
          enum "always" {
            value 2;
            description
              "Always advertise default route.";
          }
        }
        default "none";
        description
          "How a default route should be originated.";
      }
      uses metric-common-group;
    }
  }

  grouping redistribute-group {
    container redistribute {
      list routes {
        key "type";
        leaf type {
          type frr-route-types:frr-route-types-v4;
          description
            "Protocol.";
        }
        uses metric-common-group;
      }
    }
  }

  grouping summary-group {
    /* frr specific model */
    container route-aggregation {
      description
        "External route aggregation.";
      container summary-routes {
        description
          "Summaries of external routes that will be propogated by an ASBR.";
        list summary {
          key "prefix";
          leaf prefix {
            type inet:ipv4-address;
            description
              "External summary address.";
          }
          leaf tag {
            type uint32 {
              range "1..4294967295";
            }
            description
              "Router tag value";
          }
          leaf no-advertise {
            type boolean;
            default "false";
            description
              "Don't advertise this summary route.";
          }
        }
      }
      leaf timer {
        type uint16 {
          range "5..1800";
        }
        units "seconds";
        default "5";
        description
          "Aggregation delay timer.";
      }
    }
  }

  grouping preference-group {
    description
      "Route preference configuration. In the frr
       implementations, preference is also  referred to as
       administrative distance.";
    reference
      "RFC 8349: A YANG Data Model for Routing Management
       (NMDA Version)";
    container preference {
      choice scope {
        description
          "Options for expressing preference
           as single or multiple values.";
        case single-value {
          leaf all {
            type uint8 {
              range "1..255";
            }
            description
              "Admin value. Preference for intra-area, inter-area, and
               external routes.";
          }
        }
        case multi-values {
          leaf external {
            type uint8 {
              range "1..255";
            }
            description
              "Preference/Distance for external routes.";
          }
          leaf inter-area {
            type uint8 {
              range "1..255";
            }
            description
              "Preference/Distance for inter-area routes.";
          }
          leaf intra-area {
            type uint8 {
              range "1..255";
            }
            description
              "Preference/Distance for intra-area routes.";
          }
        }
      }
    }
  }

  grouping distribute-zebra-group {
    /* XXX Cannot be configured? Change to augment? */
    container distribute-from-zebra {
      list distribute {
        key "name route-type";
        description
          "Distribute List for Zebra";
        leaf name {
          type string;
          description
            "Filter networks in routing updates.";
        }
        leaf route-type {
          type frr-route-types:frr-route-types-v4;
          description
            "Out route type from Zebra.";
        }
      }
    }
  }

  grouping max-metric-group {
    container max-metric {
      container router-lsa {
        description
          "Advertise own Router-LSA with infinite distance (stub router).";
        leaf always {
          type boolean;
          default "false";
          description
            "Administratively (always) applied, for an indefinite period.";
        }
        leaf on-shutdown {
          type uint8 {
            range "5..100";
          }
          units "seconds";
          description
            "Advertise stub-router prior to full shutdown of OSPF.";
        }
        leaf on-startup {
          type uint32 {
            range "5..86400";
          }
          units "seconds";
          description
            "Automatically advertise stub Router-LSA on startup of OSPF.";
        }
      }
    }
  }

  grouping mpls-group {
    container mpls {
      container te {
        leaf on {
          /* frr specific model */
          type boolean;
          default "false";
          description
            "Enable the MPLS-TE functionality.";
        }
        leaf rid {
          type inet:ipv4-address;
          description
            "Stable IP address of the advertising router.";
        }
        container inter-as {
          /* frr specific model */
          choice mode {
            case as {
              leaf as {
                type boolean;
                description
                  "AS native mode self originate INTER-AS LSA with Type 11 (as flooding scope).";
              }
            }
            case area {
              leaf area {
                type leafref {
                  path "../../../../areas/area/area-id";
                }
                description
                  "AREA native mode self originate INTER-AS LSA with Type 10 (area flooding scope).";
              }
            }
          }
        }
      }
      container ldp {
        leaf igp-sync {
          type boolean;
          default "false";
          description
            "Enable LDP IGP synchronization.";
        }
        leaf holddown {
          /* frr specific model */
          type uint16 {
            range "0..10000";
          }
          units "seconds";
          default "0";
          description
            "LDP Holddown timer";
        }
      }
    }
  }

  grouping fast-reroute-group {
    description
      "This group defines global configuration of IP
       Fast ReRoute (FRR).";
    container fast-reroute {
      description
        "IP-FRR parameters.";
      container ti-lfa {
        description
          "Global parameters for Topology-Independent Loop-Free Alternatives
           (TI-LFA)";
        leaf protection {
          type enumeration {
            enum "undefined" {
              value 0;
              description
                "No protection in place.";
            }
            enum "link" {
              value 1;
              description
                "Protect against link failure.";
            }
            enum "node" {
              value 2;
              description
                "Protect against node failure.";
            }
          }
          default "link";
          description
            "TI-LFA Node protection type.";
        }
      }
    }
  }

  grouping ietf-spf-delay {
    description
      "Grouping for IETF SPF delay configuration and state";
    leaf delay {
      /* frr specific model */
      type uint32 {
        range "0..600000";
      }
      units "msec";
      default "0";
      description
        "Delay from first change received till SPF calculation.";
    }
    leaf initial-holdtime {
      /* frr specific model */
      type uint32 {
        range "0..600000";
      }
      units "msec";
      default "50";
      description
        "Initial hold time (msec) between consecutive SPF calculations.";
    }
    leaf max-holdtime {
      /* frr specific model */
      type uint32 {
        range "0..600000";
      }
      units "msec";
      default "5000";
      description
        "Maximum hold time (msec).";
    }
    leaf hold-multiplier {
      /* frr specific model */
      type uint32 {
        range "1..4294967295";
      }
      default "1";
      config false;
      description
        "SPF adaptive hold time multiplier.";
    }
    /*
    leaf initial-delay {
      type uint32;
      units milliseconds;
      description
        "Delay used while in QUIET state (milliseconds).";
    }
    leaf short-delay {
      type uint32;
      units milliseconds;
      description
        "Delay used while in SHORT_WAIT state (milliseconds).";
    }
    leaf long-delay {
      type uint32;
      units milliseconds;
      description
        "Delay used while in LONG_WAIT state (milliseconds).";
    }
    leaf hold-down {
      type uint32;
      units milliseconds;
      description
        "Timer used to consider an IGP stability period
         (milliseconds).";
    }
    leaf time-to-learn {
      type uint32;
      units milliseconds;
      description
        "Duration used to learn all the IGP events
         related to a single component failure (milliseconds).";
    }
    leaf current-state {
      type enumeration {
        enum "quiet" {
          description "QUIET state";
        }
        enum "short-wait" {
          description "SHORT_WAIT state";
        }
        enum "long-wait" {
          description "LONG_WAIT state";
        }
      }
      config false;
      description
        "Current SPF back-off algorithm state.";
    }
    leaf remaining-time-to-learn {
      type rt-types:timer-value-milliseconds;
      config false;
      description
        "Remaining time until time-to-learn timer fires.";
    }
    leaf remaining-hold-down {
      type rt-types:timer-value-milliseconds;
      config false;
      description
        "Remaining time until hold-down timer fires.";
    }
    leaf last-event-received {
      type yang:timestamp;
      config false;
      description
        "Time of last SPF triggering event.";
    }
    leaf next-spf-time {
      type yang:timestamp;
      config false;
      description
        "Time when next SPF has been scheduled.";
    }
    leaf last-spf-time {
      type yang:timestamp;
      config false;
      description
        "Time of last SPF computation.";
    }
    */
  }

  grouping spf-group {
    description
      "SPF calculation control.";
    container spf-control {
      leaf paths {
        type uint16 {
          range "1..65535";
        }
        default "16";
        description
          "Maximum number of Equal-Cost Multi-Path (ECMP) paths.";
      }
      container ietf-spf-delay {
        description
          "SPF delay algorithm configuration.";
        uses ietf-spf-delay;
      }
    }
  }

  grouping timer-group {
    container timers {
      leaf refresh-interval {
        type uint16 {
          range "10..1800";
        }
        units "seconds";
        default "10";
        description
          "The maximum time between distinct originations of any particular
           LSA, value in units seconds.";
      }
      leaf lsa-min-arrival {
        type uint32 {
          range "0..600000";
        }
        units "msec";
        default "1000";
        description
          "Minimum delay in receiving new version of an LSA.";
      }
      leaf lsa-min-interval {
        type uint16 {
          range "0..5000";
        }
        units "msec";
        default "5000";
        description
          "Minimum delay between LSA transmissions.";
      }
    }
  }

  /*
  grouping segment-routing-group {
    container sr-mpls {
      container srgb {
        description
          "Segment Routing Global Block label range.";
        leaf lower-bound {
          type uint32 {
            range "0..1048575";
          }
          must "../upper-bound > .";
          default "16000";
        }
        leaf upper-bound {
          type uint32 {
            range "0..1048575";
          }
          must ". > ../lower-bound";
          default "23999";
        }
      }
      container srlb {
        description
          "Local blocks to be advertised.";
        leaf lower-bound {
          type uint32;
          must "../upper-bound > .";
          default "15000";
          description
            "Lower value in the label range.";
        }
        leaf upper-bound {
          type uint32;
          must ". > ../lower-bound";
          default "15999";
          description
            "Upper value in the label range.";
        }
      }
      leaf node-msd {
        type uint8 {
          range "1..16";
        }
        description
          "Maximum Stack Depth for this router.";
      }
      leaf on {
        type boolean;
        default "false";
        description
          "Enable Segment Routing.";
      }
      container bindings {
        description
          "List of bindings.";
        container connected-prefix-sid-map {
          description
            "Prefix SID configuration.";
          list connected-prefix-sid {
            key "prefix";
            description
              "List of prefix SID mapped to IPv4 local prefixes.";
            leaf value-type {
              type enumeration {
                enum "index" {
                  description
                    "The value will be interpreted as an index.";
                }
                enum "absolute" {
                  description
                    "The value will become interpreted as an absolute value.";
                }
              }
              default "index";
              description
                "This leaf defines how the sid-value must be interpreted.";
            }
            leaf sid-value {
              type uint32;
              mandatory true;
              description
                "SID value for this prefix. See value-type for how to
                 inerpret it.";
            }
            leaf prefix {
              type inet:ipv4-prefix;
              description
                "Prefix SID.";
            }
            leaf last-hop-behavior {
              type enumeration {
                enum "explicit-null" {
                  value 0;
                  description
                    "Use explicit-null for the SID.";
                }
                enum "no-php" {
                  value 1;
                  description
                    "Do not use Penultimate Hop Popping (PHP)
                     for the SID.";
                }
                enum "php" {
                  value 2;
                  description
                    "Use PHP for the SID.";
                }
              }
              default "php";
              description
                "Configure last hop behavior.";
            }
          }
        }
      }
    }
  }
  */
  grouping ospf-list-group {
    /* XXX NBMA neighbors are stored on an interface level is the IETF model */
    container nbma-neighbors {
      description
        "Non-Broadcast Multiple Access (NBMA) neighbors.";
      list neighbor {
        key "ip";
        description
          "Neighbor list.";
        leaf ip {
          type inet:ipv4-address;
          description
            "Neighbor IP address.";
        }
        leaf priority {
          type uint8;
          default "0";
          description
            "Neighbor Priority.";
        }
        leaf poll-interval {
          type uint16 {
            range "1..65535";
          }
          units "seconds";
          default "60";
          description
            "Dead Neighbor Polling interval.";
        }
      }
    }
    container networks {
      description
        "Enable OSPF routing on list of IPv4 network.";
      list network {
        key "prefix";
        description
          "Enable routing on list of IP network.";
        leaf prefix {
          type inet:ipv4-prefix;
          description
            "Prefix on which routing needs to be enabled.";
        }
        leaf area {
          type leafref {
            path "../../../areas/area/area-id";
          }
          mandatory true;
          description
            "Area ID for this network.";
        }
      }
    }
  }

  grouping interface-common-group {
    description
      "All parameters that each interface running OSPF will require.";
    leaf ospf-id {
      /* frr specific model */
      type ospf-instance-ref;
      default "0";
      description
        "ID of OSPF routing instance that is associated with this interface.";
    }
    leaf area {
      type leafref {
        path "/frr-rt:routing/frr-rt:control-plane-protocols/"
          + "frr-rt:control-plane-protocol[frr-rt:name = "
          + "current()/../ospf-id]/ospf/areas/area/area-id";
      }
      description
        "OSPF area ID.";
    }
    uses interface-params-group {
      description
        "These are the interface parameters. They will apply to
           all addresses on the interface unless specifically overridden.";
      refine "passive" {
        default "false";
      }
      refine "priority" {
        default "1";
      }
      refine "interface-type" {
        default "broadcast";
      }
      refine "dmvpn" {
        default "false";
      }
      refine "mtu-ignore" {
        default "false";
      }
      refine "dead-interval/interval" {
        default "40";
      }
      refine "hello-interval" {
        default "10";
      }
      refine "retransmit-interval" {
        default "5";
      }
      refine "transmit-delay" {
        default "1";
      }
      refine "authentication/type" {
        default "null";
      }
      refine "mpls/ldp-sync/enable" {
        default "false";
      }
      refine "bfd/enable" {
        default "false";
      }
      refine "bfd/local-multiplier" {
        default "3";
      }
      refine "bfd/tx-rx-intervals/desired-min-tx-interval" {
        default "300";
      }
      refine "bfd/tx-rx-intervals/required-min-rx-interval" {
        default "300";
      }
    }
  }

  grouping interface-params-group {
    leaf cost {
      type ospf-link-metric;
      description
        "Configured Interface cost. If not configured, the cost of the
         interface will be in .../frr-interface:state/frr-interface:metric,
         which is automatically calculated.";
    }
    leaf passive {
      type boolean;
      description
        "Enable/Disable passive interface - a passive interface's
         prefix will be advertised but no neighbor adjacencies
         will be formed on the interface.";
    }
    leaf priority {
      type uint8;
      description
        "Configure OSPF router priority. On multi-access network
         this value is for Designated Router (DR) election. The
         priority is ignored on other interface types. A router
         with a higher priority will be preferred in the election
         and a value of 0 indicates the router is not eligible to
         become Designated Router or Backup Designated Router
         (BDR).";
    }
    leaf interface-type {
      type enumeration {
        enum "broadcast" {
          value 0;
          description
            "Specify OSPF broadcast multi-access network.";
        }
        enum "non-broadcast" {
          value 1;
          description
            "Specify OSPF Non-Broadcast Multi-Access
             (NBMA) network.";
        }
        enum "point-to-multipoint" {
          value 2;
          description
            "Specify OSPF point-to-multipoint network.";
        }
        enum "point-to-point" {
          value 3;
          description
            "Specify OSPF point-to-point network.";
        }
      }
      description
        "Interface type.";
    }
    leaf dmvpn {
      /* frr specific model */
      when "enum-value(../interface-type) = 3";
      type boolean;
      description
        "DMVPN point-to-point network is configured.";
    }
    leaf mtu-ignore {
      type boolean;
      description
        "Enable/Disable bypassing the MTU mismatch check in
         Database Description packets specified in RFC 2328,
         section 10.6.";
    }
    container dead-interval {
      leaf interval {
        type uint16 {
          range "1..65535";
        }
        units "seconds";
        description
          "Interval after which a neighbor is declared down
           (seconds) if hello packets are not received. It is
           typically 3 or 4 times the hello-interval. A typical
           value for LAN networks is 40 seconds.";
        reference
          "RFC 2328: OSPF Version 2, Appendix C.3";
      }
      container minimal {
        leaf hello-multiplier {
          type uint8 {
            range "1..10";
          }
          must "../../interval = 1" {
            /* frr specific model */
            description
              "1 second dead interval with sub-second hellos should be
               configured.";
          }
          description
            "Number of hello messages to send each second.";
        }
      }
    }
    uses interface-common-attributes;
    container mpls {
      container ldp-sync {
        leaf enable {
          type boolean;
          description
            "Turn on mpls ldp-sync.";
        }
        leaf holddown {
          type uint16 {
            range "0..10000";
          }
          units "seconds";
          description
            "Time to wait for ldp-sync to occur before restoring interface
             cost.";
        }
      }
    }
    container bfd {
      /* frr specific model */
      description
        "BFD Client Configuration.";
      leaf enable {
        type boolean;
        description
          "Enable bidirectional forwarding (BFD) on this interface.";
      }
      leaf local-multiplier {
        type uint8;
        description
          "Multiplier transmitted by the local system. Detection multiplier.";
      }
      leaf profile {
        type string;
        description
          "BFD profile.";
      }
      container tx-rx-intervals {
        leaf desired-min-tx-interval {
          type uint32;
          units "microseconds";
          description
            "Desired minimum transmit interval of control packets.";
        }
        leaf required-min-rx-interval {
          type uint32;
          units "microseconds";
          description
            "Required minimum receive interval of control packets.";
        }
      }
    }
  }

  grouping ospf-route-standard {
    /* frr specific model */
    description
      "Standard OSPF route parameters.";
    leaf area-id {
      type ospf-area-id;
      description
        "The area this route belongs to.";
    }
    leaf area-type {
      type area-type;
      description
        "Area type.";
    }
    container options {
      description
        "Optional capabilities.";
      leaf-list lsa-options {
        type identityref {
          base ospfv2-lsa-option;
        }
      }
    }
    container flags {
      description
        "Router lsa type flags.";
      leaf-list router-flags {
        type identityref {
          base router-lsa-bit;
        }
      }
    }
  }

  grouping frr-ospf-route {
    /* frr specific model */
    description
      "Additional OSPF route parameters in frr.";
    leaf destination-type {
      type destination-type;
      description
        "Destination type.";
    }
    leaf changed {
      type boolean;
      description
        "Whether or not this route has changes recently.";
    }
  }

  grouping ospf-route {
    description
      "OSPF Route";
    /* Derived from 'grouping local-rib' in ietf ospf model */
    leaf prefix {
      type inet:ipv4-prefix;
      description
        "Destination prefix.";
    }
    container next-hops {
      description
        "Next hops for the route.";
      list next-hop {
        key "next-hop";
        description
          "List of next hops for the route";
        leaf outgoing-interface {
          type frr-interface:interface-ref;
          description
            "Name of the outgoing interface.";
        }
        leaf next-hop {
          type inet:ipv4-address;
          description
            "Next hop address.";
        }
      }
    }
    leaf metric {
      type ospf-metric;
      description
        "Metric for this route.";
    }
    leaf route-type {
      type route-type;
      description
        "Route type for this route.";
    }
    /*
     * Route tag is only stored for external routes in ospfd

    leaf route-tag {
      type uint32;
      description "Route tag for this route.";
    }
    */
    uses frr-ospf-route;
  }

  grouping ospf-route-external {
    /* frr specific model */
    description
      "External OSPF route parameters.";
    leaf ls-cost {
      type uint32;
      description
        "Type 2 Link State cost.";
    }
    leaf route-tag {
      type uint32;
      description
        "Route tag for this route.";
    }
    container asbr {
      description
        "route to ASBR.";
      uses ospf-route;
      uses ospf-route-standard;
    }
  }

  grouping local-rib {
    description
      "Local-rib - RIB for Routes computed by the local
       OSPF routing instance.";
    container local-rib {
      config false;
      description
        "Local-rib.";
      list network {
        /* frr specific model */
        key "prefix";
        description
          "Network routes.";
        uses ospf-route;
        uses ospf-route-standard;
      }
      list router {
        /* frr specific model */
        key "prefix";
        description
          "Router routes.";
        uses ospf-route;
        uses ospf-route-standard;
      }
      list border {
        /* frr specific model */
        key "prefix";
        description
          "ABR/ASBR routes.";
        uses ospf-route;
        uses ospf-route-standard;
      }
      list external {
        /* frr specific model */
        key "prefix";
        description
          "External routes.";
        uses ospf-route;
        uses ospf-route-external;
      }
    }
  }

  grouping instance-fast-reroute-state {
    description
      "IP-FRR state data grouping";
    container protected-routes {
      config false;
      description
        "Instance protection statistics";
      list address-family-stats {
        key "prefix alternate";
        description
          "Per Address Family protected prefix information";
        /*
        leaf address-family {
          type iana-rt-types:address-family;
          description
            "Address-family";
        }
        */
        leaf prefix {
          type inet:ipv4-prefix;
          description
            "Protected prefix.";
        }
        leaf alternate {
          type inet:ipv4-address;
          description
            "Alternate next hop for the prefix.";
        }
        leaf alternate-type {
          type enumeration {
            enum "equal-cost" {
              description
                "ECMP alternate.";
            }
            enum "lfa" {
              description
                "LFA alternate.";
            }
            enum "remote-lfa" {
              description
                "Remote LFA alternate.";
            }
            enum "tunnel" {
              description
                "Tunnel based alternate
                 (like RSVP-TE or GRE).";
            }
            enum "ti-lfa" {
              description
                "TI-LFA alternate.";
            }
            enum "mrt" {
              description
                "MRT alternate.";
            }
            enum "other" {
              description
                "Unknown alternate type.";
            }
          }
          description
            "Type of alternate.";
        }
        leaf best {
          type boolean;
          description
            "Indicates that this alternate is preferred.";
        }
        leaf non-best-reason {
          type string {
            length "1..255";
          }
          description
            "Information field to describe why the alternate
             is not best.";
        }
        leaf protection-available {
          type bits {
            bit node-protect {
              position 0;
              description
                "Node protection available.";
            }
            bit link-protect {
              position 1;
              description
                "Link protection available.";
            }
            bit srlg-protect {
              position 2;
              description
                "SRLG protection available.";
            }
            bit downstream-protect {
              position 3;
              description
                "Downstream protection available.";
            }
            bit other {
              position 4;
              description
                "Other protection available.";
            }
          }
          description
            "Protection provided by the alternate.";
        }
        leaf alternate-metric1 {
          type uint32;
          description
            "Metric from Point of Local Repair (PLR) to
             destination through the alternate path.";
        }
        leaf alternate-metric2 {
          type uint32;
          description
            "Metric from PLR to the alternate node";
        }
        leaf alternate-metric3 {
          type uint32;
          description
            "Metric from alternate node to the destination";
        }
      }
    }
  }

  grouping frr-instance-stat {
    description
      "Additional Per-instance statistics used in frr.";
    container spf {
      description
        "SPF statistics.";
      leaf timestamp {
        type yang:timestamp;
        description
          "Timestamp of last SPF calculation.";
      }
      leaf duration {
        type int64;
        units "microseconds";
        description
          "Execution time of last SPF calculation in microseconds.";
      }
    }
  }

  grouping instance-stat {
    description
      "Per-instance statistics";
    /*
    leaf discontinuity-time {
      type yang:date-and-time;
      description
        "The time on the most recent occasion at which any one or
         more of this OSPF instance's counters suffered a
         discontinuity.  If no such discontinuities have occurred
         since the OSPF instance was last re-initialized, then
         this node contains the time the OSPF instance was
         re-initialized which normally occurs when it was
         created.";
    }
    */
    leaf originate-new-lsa-count {
      type yang:counter32;
      description
        "The number of new LSAs originated. Discontinuities in the
         value of this counter can occur when the OSPF instance is
         re-initialized.";
    }
    leaf rx-new-lsas-count {
      type yang:counter32;
      description
        "The number of new LSAs received. Discontinuities in the
         value of this counter can occur when the OSPF instance is
         re-initialized.";
    }
    /*
        leaf as-scope-lsa-count {
          type yang:gauge32;
          description "The number of AS-scope LSAs.";
        }
        leaf as-scope-lsa-chksum-sum {
          type uint32;
          description
            "The module 2**32 sum of the LSA checksums
             for AS-scope LSAs. The value should be treated as
             unsigned when comparing two sums of checksums. While
             differing checksums indicate a different combination
             of LSAs, equivalent checksums don't guarantee that the
             LSAs are the same given that multiple combinations of
             LSAs can result in the same checksum.";
        }
        container database {
          description "Container for per AS-scope LSA statistics.";
          list as-scope-lsa-type {
            description "List of AS-scope LSA statistics";
            leaf lsa-type {
              type uint16;
              description "AS-Scope LSA type.";
            }
            leaf lsa-count {
              type yang:gauge32;
              description "The number of LSAs of the LSA type.";
            }
            leaf lsa-cksum-sum {
              type uint32;
              description
                "The module 2**32 sum of the LSA checksums
                 for the LSAs of this type. The value should be
                 treated as unsigned when comparing two sums of
                 checksums. While differing checksums indicate a
                 different combination of LSAs, equivalent checksums
                 don't guarantee that the LSAs are the same given that
                 multiple combinations of LSAs can result in the same
                 checksum.";
            }
          }
        }
     */
    uses frr-instance-stat;
    // uses instance-fast-reroute-state;
  }

  grouping lsa-identifiers {
    description
      "The parameters that uniquely identify an LSA.";
    leaf area-id {
      type ospf-area-id;
      description
        "Area ID";
    }
    leaf type {
      type uint16;
      description
        "LSA type.";
    }
    leaf lsa-id {
      type inet:ipv4-address;
      description
        "Link-State ID.";
    }
    leaf adv-router {
      type rt-types:router-id;
      description
        "LSA advertising router.";
    }
    leaf seq-num {
      type uint32;
      description
        "LSA sequence number.";
    }
  }

  grouping spf-log {
    description
      "Grouping for SPF log.";
    container spf-log {
      config false;
      description
        "This container lists the SPF log.";
      list event {
        key "id";
        description
          "List of SPF log entries represented
           as a wrapping buffer in chronological
           order with the oldest entry returned
           first.";
        leaf id {
          type uint32;
          description
            "Event identifier - Purely internal value.";
        }
        leaf spf-type {
          type enumeration {
            enum "full" {
              description
                "SPF computation was a Full SPF.";
            }
            enum "intra" {
              description
                "SPF computation was only for intra-area routes.";
            }
            enum "inter" {
              description
                "SPF computation was only for inter-area
                 summary routes.";
            }
            enum "external" {
              description
                "SPF computation was only for AS external routes.";
            }
          }
          description
            "The SPF computation type for the SPF log entry.";
        }
        leaf schedule-timestamp {
          type yang:timestamp;
          description
            "This is the timestamp when the computation was
             scheduled.";
        }
        leaf start-timestamp {
          type yang:timestamp;
          description
            "This is the timestamp when the computation was
             started.";
        }
        leaf end-timestamp {
          type yang:timestamp;
          description
            "This the timestamp when the computation was
             completed.";
        }
        list trigger-lsa {
          description
            "The list of LSAs that triggered the computation.";
          uses lsa-identifiers;
        }
      }
    }
  }

  grouping lsa-log {
    description
      "Grouping for the LSA log.";
    container lsa-log {
      config false;
      description
        "This container lists the LSA log.
         Local LSA modifications are also included
         in the list.";
      list event {
        key "id";
        description
          "List of LSA log entries represented
           as a wrapping buffer in chronological order
           with the oldest entries returned first.";
        leaf id {
          type uint32;
          description
            "Event identifier - purely internal value.";
        }
        container lsa {
          description
            "This container describes the logged LSA.";
          uses lsa-identifiers;
        }
        leaf received-timestamp {
          type yang:timestamp;
          description
            "This is the timestamp when the LSA was received.
             In case of local LSA update, the timestamp refers
             to the LSA origination time.";
        }
        leaf reason {
          type identityref {
            base lsa-log-reason;
          }
          description
            "This reason for the LSA log entry.";
        }
      }
    }
  }

  grouping frr-ospf-state {
    /* frr specific model */
    description
      "Additional frr statistics for the OSPF router
       operational state.";
    container router-flags {
      config false;
      description
        "ASR/ASBR internal flags.";
      leaf-list router-flag {
        type identityref {
          base router-lsa-bit;
        }
      }
    }
    container threads {
      config false;
      description
        "All router-scope threads run in frr";
      container abr-task {
        presence "Present if the ABR task timer thread is running.";
        leaf timer {
          type int64;
          units "microseconds";
          description
            "Timer for ABR tasks in microseconds.";
        }
      }
      container asbr-check {
        presence "Present if the ASBR check timer thread is running.";
        leaf timer {
          type int64;
          units "microseconds";
          description
            "Timer for ASBR checking in microseconds.";
        }
      }
      container asbr-nssa-redist-update {
        presence "Present if the ASBR NSSA redistribution update timer is running";
        leaf timer {
          type int64;
          units "microseconds";
          description
            "Timer for ASBR NSSA updates in microseconds.";
        }
      }
      container distribute-update {
        presence "Present if the distribute list update timer thread is running.";
        leaf timer {
          type int64;
          units "microseconds";
          description
            "Timer for distributive list updates in microseconds.";
        }
      }
      container spf-calc {
        presence "Present if the SPF calculation timer thread is running.";
        leaf timer {
          type int64;
          units "microseconds";
          description
            "Timer for next shortest path first (SPF) calculations.";
        }
      }
      container ase-calc {
        presence "Present if the ASE calculation timer thread is running.";
        leaf timer {
          type int64;
          units "microseconds";
          description
            "Timer for next AS external route (ASE) calculations.";
        }
      }
      container opaque-lsa-self {
        presence "Present if type-11 opaque LSAs origin thread is running.";
        leaf timer {
          type int64;
          units "microseconds";
          description
            "Timer for type-11 opaque-LSA originination.";
        }
      }
      container sr-update {
        presence "Present if the segment routing update timer thread is running.";
        leaf timer {
          type int64;
          units "microseconds";
          description
            "Timer for next segment routing (SR) update.";
        }
      }
      container max-age {
        presence "Present if the maxage LSA remover timer thread is running.";
        leaf timer {
          type int64;
          units "microseconds";
          description
            "Max Age LSA remover timer in microseconds.";
        }
      }
      container max-age-walker {
        presence "Present if the maxage LSA checker timer thread is running.";
        leaf timer {
          type int64;
          units "microseconds";
          description
            "Max Age LSA checker timer in microseconds.";
        }
      }
      container deferred-shutdown {
        presence "Present if the deffered/stub-router shutdown timer thread is running.";
        leaf timer {
          type int64;
          units "microseconds";
          description
            "Deferred shutdown timer in microseconds.";
        }
      }
      container default-routemap-timer {
        presence "Present if the default routmap timer thread is running.";
        /* XXX It is unclear if this thread is an event or timer thread */
      }
      container lsa-refresher {
        presence "Present if the LSA refresher timer thread is running.";
        leaf timer {
          type int64;
          units "microseconds";
          description
            "Timer for next LSA refresher in microseconds.";
        }
        leaf started {
          type yang:timestamp;
          description
            "Timestamp of when LSA refresher timer started.";
        }
      }
      container external-aggr {
        presence "Present if the external aggregation timer thread is running.";
        leaf timer {
          type int64;
          units "microseconds";
          description
            "Delay timer to process external routes with summary addresses";
        }
      }
    }
    container graceful-restart {
      config false;
      description
        "Operational graceful restart information.";
      leaf active-restarter-count {
        type uint16;
        default "0";
        description
          "The number of active restarters for which this router is a helper.";
      }
      leaf last-exit-reason {
        type gr-exit-reason;
        default "exit-none";
        description
          "The last Helper exit reason.";
      }
    }
  }

  grouping ospf-state {
    description
      "OSPF router operational state.";
    uses frr-ospf-state;
    uses local-rib;
    container statistics {
      config false;
      description
        "Per-instance statistics";
      uses instance-stat;
    }
    container database {
      config false;
      description
        "AS-scope Link State Database.";
      list as-scope-lsa-type {
        key "lsa-type";
        description
          "List OSPF AS-scope LSAs.";
        leaf lsa-type {
          type uint16;
          description
            "OSPF AS scope LSA type.";
        }
        container as-scope-lsas {
          description
            "All AS-scope of LSA of this LSA type.";
          list as-scope-lsa {
            key "lsa-id adv-router";
            description
              "List of OSPF AS-scope LSAs";
            uses lsa-database;
          }
        }
      }
    }
    // uses spf-log;
    // uses lsa-log;
  }

  grouping frr-area-stat {
    /* frr specific model */
    description
      "Additional Per-area statistics kept track of in frr.";
    leaf spf-timestamp {
      type yang:timestamp;
      description
        "Timestamp of last spf calculations.";
    }
    leaf active-interfaces {
      type yang:counter32;
      description
        "The number of active interfaces in this area.";
    }
    leaf full-nbrs {
      type yang:counter32;
      description
        "The number of fully adjacent neighbors in this area.";
    }
    leaf full-virtual {
      type yang:counter32;
      description
        "The number of fully adjacent virtual neighbors in
         this area.";
    }
  }

  grouping area-stat {
    description
      "Per-area statistics.";
    /*
    leaf discontinuity-time {
      type yang:date-and-time;
      description
        "The time on the most recent occasion at which any one or
          more of this OSPF area's counters suffered a
          discontinuity.  If no such discontinuities have occurred
          since the OSPF area was last re-initialized, then
          this node contains the time the OSPF area was
          re-initialized which normally occurs when it was
          created.";
    }
    */
    leaf spf-runs-count {
      type yang:counter32;
      description
        "The number of times the intra-area SPF has run.
         Discontinuities in the value of this counter can occur
         when the OSPF area is re-initialized.";
    }
    leaf abr-count {
      type yang:gauge32;
      description
        "The total number of Area Border Routers (ABRs)
         reachable within this area.";
    }
    leaf asbr-count {
      type yang:gauge32;
      description
        "The total number of AS Boundary Routers (ASBRs).";
    }
    /*
    leaf ar-nssa-translator-event-count {
      type yang:counter32;
      description
        "The number of NSSA translator-state changes.
         Discontinuities in the value of this counter can occur
         when the OSPF area is re-initialized.";
    }
    leaf area-scope-lsa-count {
      type yang:gauge32;
      description
        "The number of area-scope LSAs in the area.";
    }
    leaf area-scope-lsa-cksum-sum {
      type uint32;
      description
        "The module 2**32 sum of the LSA checksums
         for area-scope LSAs. The value should be treated as
         unsigned when comparing two sums of checksums. While
         differing checksums indicate a different combination
         of LSAs, equivalent checksums don't guarantee that the
         LSAs are the same given that multiple combinations of
         LSAs can result in the same checksum.";
    }
    container database {
      description "Container for area-scope LSA type statistics.";
      list area-scope-lsa-type {
        description "List of area-scope LSA statistics";
        leaf lsa-type {
          type uint16;
          description "Area-scope LSA type.";
        }
        leaf lsa-count {
          type yang:gauge32;
          description "The number of LSAs of the LSA type.";
        }
        leaf lsa-cksum-sum {
          type uint32;
          description
            "The module 2**32 sum of the LSA checksums
             for the LSAs of this type. The value should be
             treated as unsigned when comparing two sums of
             checksums. While differing checksums indicate a
             different combination of LSAs, equivalent checksums
             don't guarantee that the LSAs are the same given that
             multiple combinations of LSAs can result in the same
             checksum.";
        }
      }
    }
    */
    /* XXX Should the Shortest Path Graph be modeled? */
    uses frr-area-stat;
  }

  grouping area-state {
    description
      "OSPF area operational state";
    container threads {
      description
        "All Area-scope threads run by frr.";
      container stub-router {
        presence "Present if the stub-router thread is running.";
        leaf timer {
          type int64;
          units "microseconds";
          description
            "Stub routers timer thread.";
        }
      }
      container opaque-lsa-self {
        presence "Present if type-10 opaque LSAs origin thread is running";
        leaf timer {
          type int64;
          units "microseconds";
          description
            "Timer for type-10 opaque-LSA origination.";
        }
      }
    }
    container statistics {
      description
        "Area-scope operational statistics.";
      uses area-stat;
    }
    container database {
      description
        "Area-scope Link State Database.";
      list area-scope-lsa-type {
        key "lsa-type";
        description
          "List OSPF area-scope LSAs.";
        leaf lsa-type {
          type uint16;
          description
            "OSPF area-scope LSA type";
        }
        container area-scope-lsas {
          description
            "All area-scope LSAs of an area-scope LSA type.";
          list area-scope-lsa {
            key "lsa-id adv-router";
            description
              "List of OSPF area-scope LSAs";
            uses lsa-database;
          }
        }
      }
    }
  }

  grouping frr-interface-stat {
    /* frr specific model */
    description
      "Additional statistics kept track of in frr by each interface";
    leaf hello-in {
      type yang:counter32;
      description
        "Hello message input count.";
    }
    leaf hello-out {
      type yang:counter32;
      description
        "Hello message output count.";
    }
    leaf db-desc-in {
      type yang:counter32;
      description
        "Database desc. message input count.";
    }
    leaf db-desc-out {
      type yang:counter32;
      description
        "Database desc. message output count.";
    }
    leaf ls-req-in {
      type yang:counter32;
      description
        "LS request message input count.";
    }
    leaf ls-req-out {
      type yang:counter32;
      description
        "LS request message output count.";
    }
    leaf ls-upd-in {
      type yang:counter32;
      description
        "LS update message input count.";
    }
    leaf ls-upd-out {
      type yang:counter32;
      description
        "LS update message output count.";
    }
    leaf ls-ack-in {
      type yang:counter32;
      description
        "LS ack message input count.";
    }
    leaf ls-ack-out {
      type yang:counter32;
      description
        "LS ack message output count.";
    }
    leaf discarded {
      type yang:counter32;
      description
        "Discarded input count by error.";
    }
    leaf nbrs {
      type yang:counter32;
      description
        "Number of neighbors on this interface.";
    }
    leaf full-nbrs {
      type yang:counter32;
      description
        "Number of full neighbors on this interface.";
    }
  }

  grouping interface-stat {
    description
      "Per-interface statistics";
    /*
    leaf discontinuity-time {
      type yang:date-and-time;
      description
        "The time on the most recent occasion at which any one or more of this
         OSPF interface's counters suffered a discontinuity. If no such
         discontinuities have occured since the OSPF interface was last
         re-initialized, then this node contains the time the OSPF interface
         was re-initialized which normall occurs when it was created.";
    }
    */    
    leaf if-event-count {
      type yang:counter32;
      description
        "The number of times this interface has changed its state or an error
         has occured. Discontinuities in the value of this counter can occur
         when the OSPF interface is re-initialized.";
    }
    /*
    leaf link-scope-lsa-count {
      type yang:gauge32;
      description "The number of link-scope LSAs.";
    }
    
    leaf link-scope-lsa-cksum-sum {
      type uint32;
      description
        "The module 2**32 sum of the LSA checksums for link-scope LSAs. The
         value should be treated as unsigned when comparing two sums of
         checksums. While differing checksums indicate a different combination
         of LSAs, equivalent checksums don't guarantee that the LSAs are the
         same given that multiple combinations of LSAs can result in the same
         checksum.";
    }
    
    container database {
      description "Container for link-scope LSA type statistics.";
      list link-scope-lsa-type {
        description "List of link-scope LSA statistics";
        leaf lsa-type {
          type uint16;
          description "Link scope LSA type.";
        }
        
        leaf lsa-count {
          type yang:gauge32;
          description "The number of LSAs of the LSA type.";
        }
    
        leaf lsa-cksum-sum {
          type uint32;
          description
            "The module 2**32 sum of the LSA checksums for the LSAs of this
             type. The value should be treated as unsigned when comparing two
             sums of checksums. While differing checksums indicate a different
             combination of LSAs, equivalent checksums don't guarantee that
             the LSAs are the same given that multiple combinations of LSAs
             can result in the same checksum.";
        }
      }
    }
    */
    uses frr-interface-stat;
  }

  grouping frr-neighbor-stat {
    /* frr specific model */
    description
      "Additional frr Per-neighbor statistics.";
    leaf nbr-request-qlen {
      type yang:gauge32;
      description
        "The current length of the LSA request queue. (Rqstl)";
    }
    leaf nbr-summary-len {
      type int16;
      description
        "The current length of the database summary list. (DBsml)";
    }
    leaf nbr-uptime {
      type int64;
      units "microseconds";
      description
        "The uptime of the neighbor over this interface in microseconds.";
    }
    leaf nbr-downtime {
      type int64;
      units "microseconds";
      description
        "The downtime of the neighbor over this interface in microseconds.";
    }
    container nsm {
      description
        "Neighbor state machine related statistics.";
      leaf state-changes {
        type uint32;
        description
          "The number of NSM state changes that have occured.";
      }
      leaf last-progressive {
        type int64;
        units "msec";
        description
          "Time since the last progressive NSM state change in
           milliseconds.";
      }
      leaf last-regressive {
        type int64;
        units "microseconds";
        description
          "Time since the last regressive NSM state change in
           microseconds.";
      }
    }
  }

  grouping neighbor-stat {
    description
      "Per-neighbor statistics.";
    /*
    leaf discontinuity-time {
      type yang:date-and-time;
      description
        "The time on the most recent occasion at which any one or more of this
         OSPF neighbor's counters suffered a discontinuity.  If no such
         discontinuities have occurred since the OSPF neighbor was last
         re-initialized, then this node contains the time the OSPF neighbor was
         re-initialized which normally occurs when the neighbor is dynamically
         discovered andcreated.";
    }
    
    leaf nbr-event-count {
      type yang:counter32;
      description
        "The number of times this neighbor has changed state or an error has
         occurred. Discontinuities in the value of this counter can occur when
         the OSPF neighbor is re-initialized.";
    }
    */    
    leaf nbr-retrans-qlen {
      type yang:gauge32;
      description
        "The current length of the LSA retransmission queue. (RXmtl)";
    }
    uses frr-neighbor-stat;
  }

  grouping frr-neighbor-state {
    /* frr specific model */
    description
      "Additional information frr uses to keep track of OSPF's
       neighbor operational state.";
    container threads {
      description
        "Status of frr-required neighbor threads.";
      /*
       * Some core functionality that relies on threads is already present
       * higher up in the model, and thus doesn't appear in this container.
       * (e.g. dead-timer)
       */
      container db-desc-retransmission {
        presence "Present when the database retransmission timer thread is running.";
        leaf timer {
          type int64;
          units "microseconds";
          description
            "Database description retranmission timer in microseconds";
        }
      }
      container ls-request-retransmission {
        presence "Present when the LS request retransmission timer thread is running.";
        leaf timer {
          type int64;
          units "microseconds";
          description
            "LS request retransmission timer in microseconds.";
        }
      }
      container ls-update-retransmission {
        presence "Present when the LS update retranmission timer thread is running.";
        leaf timer {
          type int64;
          units "microseconds";
          description
            "LS update retransmission timer in microseconds.";
        }
      }
      container hello-reply {
        /* 
         * XXX This thread was found in ospf_neighbor.h but didn't appear from
         * clicmd: 'show ip ospf neighbor detail json'
         */
        presence "Present when the hello reply timer thread is running.";
        leaf timer {
          type int64;
          units "microseconds";
          description
            "Time left for a neighbor to respond to a hello request, as
             measured by the hello reply thread.";
        }
      }
    }
    container graceful-restart-helper {
      /* frr specific model */
      description
        "Status of graceful restart helper";
      leaf grace-period {
        type uint32;
        units "seconds";
        description
          "The grace interval for this gr helper.";
      }
      leaf restart-reason {
        type gr-restart-reason;
        description
          "The reason for a graceful restart.";
      }
      leaf helper-status {
        type enumeration {
          enum "not-helper" {
            value 0;
            description
              "gr helper is not active.";
          }
          enum "active-helper" {
            value 1;
            description
              "gr helper is active";
          }
        }
        description
          "The gr helper's status.";
      }
      leaf helper-exit-reason {
        type gr-exit-reason;
        description
          "The reason for a gr helper exiting.";
      }
      leaf helper-rejected-reason {
        type gr-reject-reason;
        description
          "The reason a gr helper was rejected.";
      }
    }
  }

  grouping neighbor-state {
    description
      "OSPF neighbor operational state.";
    leaf address {
      type inet:ipv4-address;
      description
        "Neighbor address.";
    }
    leaf dr-router-id {
      type rt-types:router-id;
      description
        "Neighbor's Designated Router (DR) Router ID.";
    }
    leaf dr-ip-addr {
      type inet:ipv4-address;
      description
        "Neighbor's Designated Router (DR) IP address.";
    }
    leaf bdr-router-id {
      type rt-types:router-id;
      description
        "Neighbor's Backup Designated Router (BDR) Router ID.";
    }
    leaf bdr-ip-addr {
      type inet:ipv4-address;
      description
        "Neighbor's Backup Designated Router (BDR) IP Address.";
    }
    leaf state {
      type nbr-state;
      description
        "OSPF neighbor state.";
    }
    /*
    leaf cost {
      type ospf-link-metric;
      description
        "Cost to reach neighbor for Point-to-Multipoint and Hybrid networks.";
    }
    */
    leaf dead-timer {
      type rt-types:timer-value-seconds16;
      description
        "This timer tracks the remaining time before the neighbor is
         declared dead.";
    }
    container statistics {
      description
        "Per-neighbor statistics";
      uses neighbor-stat;
    }
    uses frr-neighbor-state;
  }

  grouping frr-interface-common-state {
    /* frr specific model */
    description
      "FRR specific interface operational state.";
    leaf network-lsa-seqno {
      type uint32;
      description
        "The cryptographic sequence number in use if this
         interface is the DR.";
    }
    container multicast-groups {
      description
        "The multicast groups this interface is a part of.";
      leaf ospf-all-routers {
        type boolean;
        description
          "Multicast group of all routers.";
      }
      leaf ospf-designated-routers {
        type boolean;
        description
          "Multicast group of designated routers.";
      }
    }
    container threads {
      description
        "Status of frr-required interface threads.";
      /*
       * Some core functionality that relies on threads is already present
       * higher up in the model, and thus doesn't appear in this container.
       * (e.g. hello-timer and wait-timer)
       */
      container ls-ack {
        presence "Present if the ls-ack thread is running.";
        leaf timer {
          type int64;
          units "microseconds";
          description
            "Time left in the LS ack timer thread in microseconds.";
        }
      }
      container ls-ack-direct {
        presence "Present if the LS ack event thread is running.";
      }
      container ls-upd-event {
        presence "Present if the LS update event thread is running.";
      }
      container opaque-lsa-self {
        presence "Present if the type-9 opaque-LSAs origin thread is running.";
        leaf timer {
          type int64;
          units "microseconds";
          description
            "Timer for typ 9 opaque-LSA origination.";
        }
      }
    }
  }

  /* XXX Add prefixes to each interface? */
  grouping interface-common-state {
    description
      "OSPF interface common operational state.";
    leaf state {
      type if-state;
      description
        "Interface state.";
    }
    leaf hello-timer {
      type rt-types:timer-value-seconds16;
      description
        "This timer tracks the remaining time before the next hello
         packet is sent on the interface.";
    }
    leaf wait-timer {
      type rt-types:timer-value-seconds16;
      description
        "This timer tracks the remaining time before the interface exits
         the waiting state.";
    }
    leaf dr-router-id {
      type rt-types:router-id;
      description
        "Designated Router (DR) Router ID.";
    }
    leaf dr-ip-addr {
      type inet:ipv4-address;
      description
        "Designated Router (DR) IP address.";
    }
    leaf bdr-router-id {
      type rt-types:router-id;
      description
        "Backup Designated Router (BDR) Router ID.";
    }
    leaf bdr-ip-addr {
      type inet:ipv4-address;
      description
        "Backup Designated Router (BDR) IP Address.";
    }
    uses frr-interface-common-state;
    container statistics {
      description
        "Per-interface statistics";
      uses interface-stat;
    }
    container neighbors {
      description
        "All neighbors for the interface.";
      list neighbor {
        key "neighbor-router-id";
        description
          "List of interface OSPF neighbors.";
        leaf neighbor-router-id {
          type rt-types:router-id;
          description
            "Neighbor Router ID.";
        }
        uses neighbor-state;
      }
    }
    container database {
      description
        "Link-scope Link State Database.";
      list link-scope-lsa-type {
        key "lsa-type";
        description
          "List OSPF link-scope LSAs.";
        leaf lsa-type {
          type uint16;
          description
            "OSPF link-scope LSA type.";
        }
        container link-scope-lsas {
          description
            "All link-scope LSAs of this LSA type.";
          list link-scope-lsa {
            key "lsa-id adv-router";
            description
              "List of OSPF link-scope LSAs";
            uses lsa-database;
          }
        }
      }
    }
  }

  grouping interface-address-group {
    description
      "Configuration for overriding the base interface config parameters.";
    leaf address {
      type inet:ipv4-address;
      description
        "An interface address to override OSPF parameters on.";
    }
    leaf area {
      type leafref {
        path "/frr-rt:routing/frr-rt:control-plane-protocols/"
          + "frr-rt:control-plane-protocol[frr-rt:name = "
          + "current()/../../ospf-id]/ospf/areas/area/area-id";
      }
      description
        "OSPF area ID.";
    }
    uses interface-params-group;
  }

  augment "/frr-rt:routing/frr-rt:control-plane-protocols/frr-rt:control-plane-protocol" {
    description "Adds OSPF to routing model";
    container ospf {
      when "../frr-rt:type = 'frr-ospfd:ospf'" {
        description
          "This container is only valid for the 'OSPF' routing
           protocol.";
      }
      description
        "Global ospf configuration and operational state.";
      uses route-ospf-attributes;
      uses graceful-restart-group;
      uses auto-cost-group;
      uses default-info-group;
      uses redistribute-group;
      uses summary-group;
      uses preference-group;
      uses distribute-zebra-group;
      uses max-metric-group;
      uses mpls-group;
      uses fast-reroute-group;
      uses spf-group;
      uses timer-group;
      // uses segment-routing-group;
      uses ospf-list-group;
      container state {
        config false;
        /* 
         * ietf model doesn't have a container for state, it only intermixes it
         */
        description
          "Container for Router-scope operational state.";
        uses ospf-state;
      }
      uses area-groupings;
    }
  }
  augment "/frr-interface:lib/frr-interface:interface" {
    container ospf {
      presence "Present if OSPF is running on this interface.";
      description
        "OSPF interface parameters.";
      uses interface-common-group;
      list interface-address {
        key "address";
        description
          "OSPF interface parameters to override the default OSPF interface
           parameters on a per-address basis.";
        uses interface-address-group;
      }
      container state {
        config false;
        description
          "OSPF interface's operational state.";
        uses interface-common-state;
      }
    }
  }
  
  /*
   * ----------------------------
   * Remote Procedure Calls (RPC)
   * ----------------------------
   */

  rpc clear-ospf-interface {
    description
      "Clears OSPF interfaces from instances of OSPF.";

    input {
      leaf vrf {
        type frr-vrf:vrf-ref;
        description
          "VRF name identifying a specific OSPF instace.
           This leaf is optional for the rpc.
           If it is specified, the rpc will clear some set of interfaces in the
           specified OSPF instance.
           If it is not specified, the rpc will clear some set of interfaces in
           all OSPF instances.";
      }
      leaf interface-name {
        type frr-interface:interface-ref;
        description
          "Interface name identifying a specific instance of OSPF on an
           interface.
           This leaf is optional for the rpc.
           If it is specified, the rpc will clear only the specific interface
           in some set of OSPF instances.
           If it is not specified, the rpc will clear all interfaces in some
           set of OSPF instances.";
      }
    }
  }
  rpc clear-ospf-neighbor {
    description
      "Clears OSPF neighbors from instances of OSPF.";

    input {
      leaf ospf-instance {
        type ospf-instance-ref;
        description
          "uint16 integer identifying a specific OSPF instace.
           This leaf is optional for the rpc.
           If it is specified, the rpc will clear some set of neighbors in the
           specified OSPF instance.
           If it is not specified, the rpc will clear some set of neighbors in
           all OSPF instances.";
      }
      leaf neighbor {
        type neighbor-ref;
        description
          "The routing ID identifying a specific neighbor.
           This leaf is optional for the rpc.
           If it is specified, the rpc will clear only the specified neighbor
           in some set of OSPF instances.
           If it is not specified, the rpc will clear all neighbors in some set
           of OSPF instances.";
      }
    }
  }
  rpc clear-ospf-process {
    description
      "Clears en entire OSPF process.";

    input {
      leaf ospf-instance {
        type ospf-instance-ref;
        description
          "uint16 integer identifying a specific OSPF instace.
           This leaf is optional for the rpc.
           If it is specified, the rpc will clear only the specified
           OSPF process.
           If it is not specified, the rpc will clear all OSPF processes.";
      }
    }
  }
}
